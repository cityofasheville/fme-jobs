FME workspace bc_property-to-edit.fmw

Parameters:
- coa-edit-sde = C:\Users\mssqlgisadmin\AppData\Roaming\ESRI\Desktop10.2\ArcCatalog\coa-gis-edit1.sde   # Connection File

Readers:
- GEODATABASE_SDE_1: GEODATABASE_SDE

Writers:
- GEODATABASE_SDE_2: GEODATABASE_SDE

DBO.property (reader GEODATABASE_SDE_1)
    attributes: OBJECTID integer, PINNUM char(50), PIN char(15), PINEXT char(50), OWNER char(50), NMPTYPE integer, TAXYEAR char(50), CONDOUNIT char(50), CONDOBUILDING char(50), DEEDBOOK char(50), DEEDPAGE char(50), PLATBOOK char(50), PLATPAGE char(50), SUBNAME char(50), SUBLOT char(50), SUBBLOCK char(50), SUBSECT char(50), UPDATEDATE char(50), HOUSENUMBER char(50), NUMBERSUFFIX char(50), DIRECTION char(50), STREETNAME char(50), STREETTYPE char(50), TOWNSHIP char(50), ACREAGE double, ACCOUNTNUMBER char(50), DEEDDATE char(50), STAMPS double, INSTRUMENT char(50), REASON char(50),
      COUNTY char(50), CITY char(50), FIREDISTRICT char(50), SCHOOLDISTRICT char(50), CAREOF char(50), ADDRESS char(50), CITYNAME char(50), STATE char(50), ZIPCODE char(50), CLASS char(50), IMPROVED char(50), EXEMPT char(50), PRICED char(50), TOTALMARKETVALUE integer, APPRAISEDVALUE integer, TAXVALUE integer, LANDUSE char(50), NEIGHBORHOODCODE char(50), LANDVALUE integer, BUILDINGVALUE integer, IMPROVEMENTVALUE integer, APPRAISALAREA char(50), STATE_ROUTE char(50), STATE_ROUTE_SUFFIX char(50), PROPCARD char(150), Shape.area double, Shape.len double
    -> ownertrim
ownertrim: AttributeTrimmer
    TRIM_TO_NONE = Yes
    TRIM_TYPE = Both
    SRC_ATTRS = OWNER
    -> coagis.bc_property (writer GEODATABASE_SDE_2)
coagis.bc_property (writer GEODATABASE_SDE_2)
    attributes: objectid integer, pinnum char(50), pin char(15), pinext char(50), owner char(50), nmptype char(150), taxyear char(50), condounit char(50), condobuilding char(50), deedbook char(50), deedpage char(50), platbook char(50), platpage char(50), subname char(50), sublot char(50), subblock char(50), subsect char(50), updatedate char(50), housenumber char(50), numbersuffix char(50), direction char(50), streetname char(50), streettype char(50), township char(50), acreage double, accountnumber char(50), deeddate char(50), stamps double, instrument char(50), reason char(50),
      county char(50), city char(50), firedistrict char(50), schooldistrict char(50), careof char(50), address char(50), cityname char(50), state char(50), zipcode char(50), class char(50), improved char(50), exempt char(50), priced char(50), totalmarketvalue double, appraisedvalue double, taxvalue double, landuse char(50), neighborhoodcode char(50), landvalue double, buildingvalue double, improvementvalue double, appraisalarea char(50), state_route char(50), state_route_suffix char(50), propcard char(150), oldpinnum char(50), citystatezip char(50), st_area(shape) double, st_length(shape) double
