FME workspace bc_street_history_to-warehouse.fmw

Parameters:
- DestDataset_POSTGIS = coa-gis-warehouse1   # Connection

Readers:
- GEODATABASE_SDE_1: GEODATABASE_SDE

Writers:
- POSTGIS_1: POSTGIS to $(DestDataset_POSTGIS)

DBO.centerline_history (reader GEODATABASE_SDE_1)
    attributes: OBJECTID integer, CENTERLINE_ID double, ROAD_CLASS integer, STREET_PREFIX char(2), STREET_NAME char(30), STREET_TYPE char(4), STREET_POSTDIRECTION char(2), STREET_DUPE char(1), FULL_STREET_NAME char(32), COMMUNITY_CODE char(4), SPEED_LIMIT integer, LANE_COUNT integer, LEFT_FROM_ADDRESS integer, LEFT_TO_ADDRESS integer, RIGHT_FROM_ADDRESS integer, RIGHT_TO_ADDRESS integer, USER_ID char(8), CREATE_DATE date, CHANGE_DATE date, LESN smallint, RESN smallint, LZIP integer, RZIP integer, LCOMMCODE char(4), RCOMMCODE char(4), ROUTE_ID char(20), SHAPE.STLength() double
    -> CREATE_DATE2
CREATE_DATE2: DateFormatter
    DATE_ATTR = CREATE_DATE,CHANGE_DATE
    FMT = FME Date/Time (%Y%m%d%H%M%S)
    SRCFMT = Unknown - Automatic Detection
    INVALID_DATE_VALUE = _FME_NO_OP_
    -> coagis.bc_street_history (writer POSTGIS_1)
coagis.bc_street_history (writer POSTGIS_1)
    attributes: objectid int4,PRIKEY, centerline_id numeric(38,8), road_class int4, street_prefix varchar(2), street_name varchar(30), street_type varchar(4), street_postdirection varchar(2), street_dupe varchar(1), full_street_name varchar(32), community_code varchar(4), speed_limit int4, lane_count int4, left_from_address int4, left_to_address int4, right_from_address int4, right_to_address int4, user_id varchar(8), create_date timestamp, change_date timestamp, lesn int4, resn int4, lzip int4, rzip int4, lcommcode varchar(4), rcommcode varchar(4), route_id varchar(20)
