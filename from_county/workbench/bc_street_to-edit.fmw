FME workspace bc_street_to-edit.fmw

Readers:
- GEODATABASE_SDE_1: GEODATABASE_SDE

Writers:
- GEODATABASE_SDE_2: GEODATABASE_SDE

DBO.CENTERLINE (reader GEODATABASE_SDE_1)
    attributes: OBJECTID integer, CENTERLINE_ID double, ROAD_CLASS integer, STREET_PREFIX char(2), STREET_NAME char(30), STREET_TYPE char(4), STREET_POSTDIRECTION char(2), STREET_DUPE char(1), FULL_STREET_NAME char(32), SPEED_LIMIT integer, LANE_COUNT integer, LEFT_FROM_ADDRESS integer, LEFT_TO_ADDRESS integer, RIGHT_FROM_ADDRESS integer, RIGHT_TO_ADDRESS integer, USER_ID char(8), CREATE_DATE date, CHANGE_DATE date, LESN smallint, RESN smallint, LZIP integer, RZIP integer, LCOMMCODE char(4), RCOMMCODE char(4), ROUTE_ID char(20), shape.len double
    -> coagis.bc_street (writer GEODATABASE_SDE_2)
coagis.bc_street (writer GEODATABASE_SDE_2)
    attributes: objectid integer, centerline_id double, road_class integer, street_prefix char(2), street_name char(30), street_type char(4), street_postdirection char(2), street_dupe char(1), full_street_name char(32), speed_limit integer, lane_count integer, left_from_address integer, left_to_address integer, right_from_address integer, right_to_address integer, user_id char(8), create_date date, change_date date, lesn smallint, resn smallint, lzip integer, rzip integer, lcommcode char(4), rcommcode char(4), route_id char(20), maximo_type char(30), maximo_seq_num integer, asset_code char(50), mrc char(8), min_range integer,
      max_range integer, st_length(shape) double
