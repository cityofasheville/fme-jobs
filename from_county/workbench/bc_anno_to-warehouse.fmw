FME workspace bc_anno_to-warehouse.fmw

Parameters:
- SourceDataset_SDE30_3 = bun   # Source ESRI ArcSDE Dataset
- DestDataset_POSTGIS_3 = coa-gis-warehouse1b   # Connection

Readers:
- SDE30_1: SDE30 from $(SourceDataset_SDE30_3)

Writers:
- POSTGIS_1: POSTGIS to $(DestDataset_POSTGIS_3)

DBO.PROPDIM_ANNO_2015 (reader SDE30_1)
    attributes: OBJECTID integer, FeatureID integer, ZOrder integer, AnnotationClassID integer, Element blob, SymbolID integer, Status smallint, TextString char(255), FontName char(255), FontSize double, Bold smallint, Italic smallint, Underline smallint, VerticalAlignment smallint, HorizontalAlignment smallint, XOffset double, YOffset double, Angle double, FontLeading double, WordSpacing double, CharacterWidth double, CharacterSpacing double, FlipAngle double, Override integer, X double, Y double, OFFSETX double, OFFSETY double, HEIGHT double, SYMBOL integer,
      LEVEL_ integer, TEXT_ char(255), REC_ integer, FEATURE_KEY integer, DIM_ integer, DIM_ID integer, ID integer, SYMBOL_1 integer, LEVEL_1 integer
    -> coagis.bc_propdim_anno (writer POSTGIS_1)
coagis.bc_propdim_anno (writer POSTGIS_1)
    attributes: objectid int4, featureid int4, zorder int4, annotationclassid int4, element bytea, symbolid int4, status int2, textstring varchar(255), fontname varchar(255), fontsize numeric(38,8), bold int2, italic int2, underline int2, verticalalignment int2, horizontalalignment int2, xoffset numeric(38,8), yoffset numeric(38,8), angle numeric(38,8), fontleading numeric(38,8), wordspacing numeric(38,8), characterwidth numeric(38,8), characterspacing numeric(38,8), flipangle numeric(38,8), override int4, dim_ int4, dim_id int4, x numeric(38,8), y numeric(38,8), offsetx numeric(38,8), offsety numeric(38,8),
      height numeric(38,8), symbol int4, level_ int4, text_ varchar(255), rec_ int4, id int4, symbol_1 int4, level_1 int4, feature_key int4
