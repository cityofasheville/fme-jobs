FME workspace bc_civic_address_table-to-warehouse.fmw

Parameters:
- DestDataset_POSTGRES = coa-gis-warehouse1-TABLE   # Connection

Readers:
- GEODATABASE_SDE_1: GEODATABASE_SDE

Writers:
- POSTGRES_1: POSTGRES to $(DestDataset_POSTGRES)

DBO.CIVICADDRESSTBL (reader GEODATABASE_SDE_1)
    attributes: OBJECTID integer, CIVICADDRESS_ID double, LOCATION_ID double, STREET_NUMBER integer, UNIT char(4), UNIT_TYPE integer, STREET_PREFIX char(2), STREET_NAME char(30), STREET_TYPE char(4), STREET_POSTDIRECTION char(2), FULL_CIVIC_ADDRESS char(40), CREATE_DATE date, CHANGE_DATE date, USER_ID char(8), POSTAL_CODE integer, COMMCODE char(4), STREET_DUPE char(3), PINEXT char(5)
    -> coagis.bc_civicaddress_table (writer POSTGRES_1)
coagis.bc_civicaddress_table (writer POSTGRES_1)
    attributes: objectid int4,PRIKEY, civicaddress_id float8, location_id float8, street_number int4, unit char(4), unit_type int4, street_prefix char(2), street_name char(30), street_type char(4), street_postdirection char(2), full_civic_address char(40), create_date date, change_date date, user_id char(8), postal_code int4, commcode char(4), street_dupe char(3), pinext char(5)
