FME workspace coa_water_underground_enclosure.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_water_underground_enclosure (reader POSTGIS_1)
    attributes: objectid int4,PRIKEY, facilityid varchar(20), installdate timestamp, subtype varchar(100), workorderid varchar(20), elevation numeric(38,8), covermaterial varchar(150), covertype varchar(20), depth numeric(38,8), invertelevation numeric(38,8), operationalarea varchar(150), lifecyclestatus varchar(150), locationdescription varchar(75), last_mod_date timestamp, last_mod_by varchar(32), maximo_type varchar(30), maximo_seq_num int4, asset_code varchar(50), mrc varchar(8), edit_date timestamp, edit_by varchar(100)
    -> coagis.coa_water_underground_enclosure (writer POSTGIS_2)
coagis.coa_water_underground_enclosure (writer POSTGIS_2)
    attributes: objectid int4,PRIKEY, facilityid varchar(20), installdate timestamp, subtype varchar(100), workorderid varchar(20), elevation numeric(38,8), covermaterial varchar(150), covertype varchar(20), depth numeric(38,8), invertelevation numeric(38,8), operationalarea varchar(150), lifecyclestatus varchar(150), locationdescription varchar(75), last_mod_date timestamp, last_mod_by varchar(32), maximo_type varchar(30), maximo_seq_num int4, asset_code varchar(50), mrc varchar(8), edit_date timestamp, edit_by varchar(100)
