FME workspace coa_districts_snow_removal.fmw

Parameters:
- SourceDataset_POSTGIS = coa-gis-edit1b   # Connection
- DestDataset_POSTGIS = coa-gis-warehouse1   # Connection

Readers:
- POSTGIS_1: POSTGIS from $(SourceDataset_POSTGIS)

Writers:
- POSTGIS_2: POSTGIS to $(DestDataset_POSTGIS)

coagis.coa_districts_snow_removal (reader POSTGIS_1)
    attributes: objectid int4,PRIKEY, name varchar(10), edit_date timestamp, edit_by varchar(100)
    -> coagis.coa_districts_snow_removal (writer POSTGIS_2)
coagis.coa_districts_snow_removal (writer POSTGIS_2)
    attributes: objectid int4,PRIKEY, name varchar(10), edit_date timestamp, edit_by varchar(100)
