FME workspace coa_water_hydrant.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_water_hydrant (reader POSTGIS_1)
    attributes: objectid int4,PRIKEY, facilityid varchar(20), installdate timestamp, lifecyclestatus varchar(150), workorderid varchar(20), elevation numeric(38,8), source varchar(150), oldwaterdepartment int4, operationalarea varchar(150), locationdescription varchar(50), maindiameter varchar(150), last_mod_date timestamp, last_mod_by varchar(32), maximo_type varchar(30), maximo_seq_num int4, asset_code varchar(50), mrc varchar(8), agency varchar(150), edit_date timestamp, edit_by varchar(100), houseno int2, streetname varchar(35), hydrantmake varchar(25), hydrantmodel varchar(50), hydrantyear int2, valvepresent varchar(3), district varchar(3), bonnetcolor varchar(3), hydrant_type varchar(50), date_removed timestamp
    -> coagis.coa_water_hydrant (writer POSTGIS_2)
coagis.coa_water_hydrant (writer POSTGIS_2)
    attributes: objectid int4,PRIKEY, facilityid varchar(20), installdate timestamp, lifecyclestatus varchar(150), workorderid varchar(20), elevation numeric(38,8), source varchar(150), oldwaterdepartment int4, operationalarea varchar(150), locationdescription varchar(50), maindiameter varchar(150), last_mod_date timestamp, last_mod_by varchar(32), maximo_type varchar(30), maximo_seq_num int4, asset_code varchar(50), mrc varchar(8), agency varchar(150), edit_date timestamp, edit_by varchar(100), houseno int4, streetname varchar(35), hydrantmake varchar(25), hydrantmodel varchar(50), hydrantyear int4, valvepresent varchar(10), district varchar(10), bonnetcolor varchar(10), hydrant_type varchar(50), date_removed timestamp
