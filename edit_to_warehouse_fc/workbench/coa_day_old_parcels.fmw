FME workspace coa_day_old_parcels.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_day_old_parcels (reader POSTGIS_1)
    attributes: objectid int4,PRIKEY, pinnum varchar(50), pin varchar(15), pinext varchar(50), owner varchar(50), nmptype int2, taxyear varchar(50), condounit varchar(50), condobuilding varchar(50), deedbook varchar(50), deedpage varchar(50), platbook varchar(50), platpage varchar(50), subname varchar(50), sublot varchar(50), subblock varchar(50), subsect varchar(50), updatedate varchar(50), housenumber varchar(50), numbersuffix varchar(50), direction varchar(50), streetname varchar(50), streettype varchar(50), township varchar(50), acreage numeric(38,8), accountnumber varchar(50), deeddate varchar(50), stamps numeric(38,8), instrument varchar(50), reason varchar(50),
      county varchar(50), city varchar(50), firedistrict varchar(50), schooldistrict varchar(50), careof varchar(50), address varchar(50), cityname varchar(50), state varchar(50), zipcode varchar(50), class varchar(50), improved varchar(50), exempt varchar(50), priced varchar(50), totalmarketvalue varchar(50), appraisedvalue varchar(50), taxvalue varchar(50), landuse varchar(50), neighborhoodcode varchar(50), landvalue varchar(50), buildingvalue varchar(50), improvementvalue varchar(50), appraisalarea varchar(50), state_route varchar(50), state_route_suffix varchar(50), propcard varchar(150), oldpinnum varchar(12), edit_date timestamp, edit_by varchar(100)
    -> coagis.coa_day_old_parcels (writer POSTGIS_2)
coagis.coa_day_old_parcels (writer POSTGIS_2)
    attributes: objectid int4,PRIKEY, pinnum varchar(50), pin varchar(15), pinext varchar(50), owner varchar(50), nmptype int4, taxyear varchar(50), condounit varchar(50), condobuilding varchar(50), deedbook varchar(50), deedpage varchar(50), platbook varchar(50), platpage varchar(50), subname varchar(50), sublot varchar(50), subblock varchar(50), subsect varchar(50), updatedate varchar(50), housenumber varchar(50), numbersuffix varchar(50), direction varchar(50), streetname varchar(50), streettype varchar(50), township varchar(50), acreage numeric(38,8), accountnumber varchar(50), deeddate varchar(50), stamps numeric(38,8), instrument varchar(50), reason varchar(50),
      county varchar(50), city varchar(50), firedistrict varchar(50), schooldistrict varchar(50), careof varchar(50), address varchar(50), cityname varchar(50), state varchar(50), zipcode varchar(50), class varchar(50), improved varchar(50), exempt varchar(50), priced varchar(50), totalmarketvalue varchar(50), appraisedvalue varchar(50), taxvalue varchar(50), landuse varchar(50), neighborhoodcode varchar(50), landvalue varchar(50), buildingvalue varchar(50), improvementvalue varchar(50), appraisalarea varchar(50), state_route varchar(50), state_route_suffix varchar(50), propcard varchar(150), oldpinnum varchar(25), edit_date timestamp, edit_by varchar(100)
