FME workspace coa_water_connection_questions.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_water_connection_questions (reader POSTGIS_1)
    attributes: objectid int4,PRIKEY, comment varchar(150), pot_connection varchar(20), field_verified varchar(15), gis_existing varchar(10), connection_type varchar(20), coa_verify varchar(50), edit_date timestamp, edit_by varchar(100)
    -> coagis.coa_water_connection_questions (writer POSTGIS_2)
coagis.coa_water_connection_questions (writer POSTGIS_2)
    attributes: objectid int4,PRIKEY, comment varchar(150), pot_connection varchar(20), field_verified varchar(15), gis_existing varchar(10), connection_type varchar(20), coa_verify varchar(50), edit_date timestamp, edit_by varchar(100)
