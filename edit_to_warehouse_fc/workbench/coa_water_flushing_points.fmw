FME workspace coa_water_flushing_points.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_water_flushing_points (reader POSTGIS_1)
    attributes: objectid int4,PRIKEY, address varchar(150), setting varchar(150), type varchar(150), plant varchar(50), last_mod_date timestamp, last_mod_by varchar(32), maximo_type varchar(30), maximo_seq_num int4, asset_code varchar(50), mrc varchar(8), edit_date timestamp, edit_by varchar(100)
    -> coagis.coa_water_flushing_points (writer POSTGIS_2)
coagis.coa_water_flushing_points (writer POSTGIS_2)
    attributes: objectid int4, address varchar(150), setting varchar(150), type varchar(150), plant varchar(50), last_mod_date timestamp, last_mod_by varchar(32), maximo_type varchar(30), maximo_seq_num int4, asset_code varchar(50), mrc varchar(8), edit_date timestamp, edit_by varchar(100)
