FME workspace coa_water_control_valve.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_water_control_valve (reader POSTGIS_1)
    attributes: objectid int4,PRIKEY, facilityid varchar(20), installdate timestamp, locationdescription varchar(200), lifecyclestatus varchar(150), subtype varchar(150), workorderid varchar(20), elevation numeric(38,8), operationalarea varchar(150), source varchar(150), diameter varchar(150), last_mod_date timestamp, last_mod_by varchar(32), maximo_type varchar(30), maximo_seq_num int4, asset_code varchar(50), mrc varchar(8), edit_date timestamp, edit_by varchar(100)
    -> coagis.coa_water_control_valve (writer POSTGIS_2)
coagis.coa_water_control_valve (writer POSTGIS_2)
    attributes: objectid int4,PRIKEY, facilityid varchar(20), installdate timestamp, locationdescription varchar(200), lifecyclestatus varchar(150), subtype varchar(150), workorderid varchar(20), elevation numeric(38,8), operationalarea varchar(150), source varchar(150), diameter varchar(150), last_mod_date timestamp, last_mod_by varchar(32), maximo_type varchar(30), maximo_seq_num int4, asset_code varchar(50), mrc varchar(8), edit_date timestamp, edit_by varchar(100)
