FME workspace coa_stormwater_customer_parcels.fmw

Parameters:
- SourceDataset_POSTGIS = coa-gis-edit1b   # Connection
- DestDataset_POSTGIS = coa-gis-warehouse1   # Connection

Readers:
- POSTGIS_1: POSTGIS from $(SourceDataset_POSTGIS)

Writers:
- POSTGIS_2: POSTGIS to $(DestDataset_POSTGIS)

coagis.coa_stormwater_customer_parcels (reader POSTGIS_1)
    attributes: objectid int4,PRIKEY, pinnum varchar(12), owner varchar(35), careof varchar(30), addr varchar(30), cityname varchar(17), state varchar(2), zip int4, class varchar(3), propcard varchar(150), eru int4, customertype varchar(2), cycle int4, route int4, custid numeric(38,8), locid numeric(38,8), accountnumber varchar(25), erusource varchar(150), unibill varchar(150), pin varchar(15), oldpinnum varchar(15), edit_date timestamp, edit_by varchar(100)
    -> coagis.coa_stormwater_customer_parcels (writer POSTGIS_2)
coagis.coa_stormwater_customer_parcels (writer POSTGIS_2)
    attributes: objectid int4,PRIKEY, pinnum varchar(12), owner varchar(35), careof varchar(30), addr varchar(30), cityname varchar(17), state varchar(2), zip int4, class varchar(3), propcard varchar(150), eru int4, customertype varchar(2), cycle int4, route int4, custid numeric(38,8), locid numeric(38,8), accountnumber varchar(25), erusource varchar(150), unibill varchar(150), pin varchar(15), oldpinnum varchar(15), edit_date timestamp, edit_by varchar(100)
