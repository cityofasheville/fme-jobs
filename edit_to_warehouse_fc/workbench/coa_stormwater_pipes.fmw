FME workspace coa_stormwater_pipes.fmw

Parameters:
- SourceDataset_POSTGIS = coa-gis-edit1b   # Connection
- DestDataset_POSTGIS = coa-gis-warehouse1   # Connection

Readers:
- POSTGIS_1: POSTGIS from $(SourceDataset_POSTGIS)

Writers:
- POSTGIS_2: POSTGIS to $(DestDataset_POSTGIS)

coagis.coa_stormwater_pipes (reader POSTGIS_1)
    attributes: objectid int4,PRIKEY, entity varchar(14), layer varchar(32), elevation numeric(38,8), thickness numeric(38,8), color int4, ddm int2, updatedby varchar(20), diameter int2, material varchar(20), invin numeric(38,8), invout numeric(38,8), length numeric(38,8), slope numeric(38,8), enabled int2, diamat varchar(25), projname varchar(25), newrepasbuilt varchar(2), edit_date timestamp, edit_by varchar(100)
    -> 2DForcer
2DForcer
    2D -> coagis.coa_stormwater_pipes (writer POSTGIS_2)
coagis.coa_stormwater_pipes (writer POSTGIS_2)
    attributes: objectid int4,PRIKEY, entity varchar(14), layer varchar(32), elevation numeric(38,8), thickness numeric(38,8), color int4, ddm int4, updatedby varchar(20), diameter int4, material varchar(20), invin numeric(38,8), invout numeric(38,8), length numeric(38,8), slope numeric(38,8), enabled int4, diamat varchar(25), projname varchar(25), newrepasbuilt varchar(2), edit_date timestamp, edit_by varchar(100)
