FME workspace coa_homeless_service_organizations.fmw

Parameters:
- SourceDataset_POSTGIS = coa-gis-edit1b   # Connection
- DestDataset_POSTGIS = coa-gis-warehouse1b   # Connection
- DestDataset_POSTGIS_4 = coa-gis-warehouse1b   # Connection

Readers:
- POSTGIS_1: POSTGIS from $(SourceDataset_POSTGIS)

Writers:
- POSTGIS_2: POSTGIS to $(DestDataset_POSTGIS)
- POSTGIS_3: POSTGIS to $(DestDataset_POSTGIS_4)

coagis.coa_homeless_service_organizations (reader POSTGIS_1)
    attributes: objectid int4,PRIKEY, name_id varchar(50), comments varchar(50), edit_date timestamp, edit_by varchar(100)
    -> coagis.coa_homeless_service_organizations (writer POSTGIS_3)
coagis.coa_homeless_service_organizations (writer POSTGIS_3)
    attributes: objectid int4,PRIKEY, name_id varchar(50), comments varchar(50), edit_by varchar(100), edit_date timestamp
