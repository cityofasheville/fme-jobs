FME workspace coa_fire_station_response_distance_road.fmw

Parameters:
- SourceDataset_POSTGIS = coa-gis-edit1   # Connection
- DestDataset_POSTGIS = coa-gis-warehouse1   # Connection

Readers:
- POSTGIS_1: POSTGIS from $(SourceDataset_POSTGIS)

Writers:
- POSTGIS_2: POSTGIS to $(DestDataset_POSTGIS)

coagis.coa_fire_station_response_distance_road (reader POSTGIS_1)
    attributes: objectid int4,PRIKEY, facilityid int4, from_distance numeric(38,8), to_distance numeric(38,8), from_traveltime numeric(38,8), to_traveltime numeric(38,8), stationname varchar(20), category varchar(10), distance int2, edit_date timestamp, edit_by varchar(100)
    -> coagis.coa_fire_station_response_distance_road (writer POSTGIS_2)
coagis.coa_fire_station_response_distance_road (writer POSTGIS_2)
    attributes: objectid int4,PRIKEY, facilityid int4, from_distance numeric(38,8), to_distance numeric(38,8), from_traveltime numeric(38,8), to_traveltime numeric(38,8), stationname varchar(20), category varchar(10), distance int4, edit_date timestamp, edit_by varchar(100)
