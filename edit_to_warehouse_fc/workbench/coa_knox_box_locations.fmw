FME workspace coa_knox_box_locations.fmw

Parameters:
- DestDataset_POSTGIS = coa-gis-warehouse1b   # Connection
- SourceDataset_POSTGIS = coa-gis-edit1b   # Connection
- DestDataset_POSTGIS_4 = coa-gis-warehouse1b   # Connection

Readers:
- POSTGIS_1: POSTGIS from $(SourceDataset_POSTGIS)

Writers:
- POSTGIS_2: POSTGIS to $(DestDataset_POSTGIS)
- POSTGIS_3: POSTGIS to $(DestDataset_POSTGIS_4)

coagis.coa_knox_box_locations (reader POSTGIS_1)
    attributes: objectid int4,PRIKEY, site_seq numeric(15,0), dept_seq numeric(15,0), oth_seq numeric(15,0), addtime timestamp, adduser varchar(100), site_name varchar(80), modmark varchar(50), mailmlifk numeric(15,0), street_num varchar(50), stprefix varchar(50), address1 varchar(60), sttype varchar(50), stsuffix varchar(50), address2 varchar(60), stinter int2, insp_type varchar(50), insp_freq numeric(38,8), last_insp timestamp, insp_due timestamp, comp_due timestamp, lnoncomply int2, lactive int2, ppreview timestamp, ppreviewer varchar(50), fireflow_ci varchar(50), fireflow_co varchar(50), fireflow_oi varchar(50), fireflow_xi varchar(50), baseflow varchar(50),
      fireflow_si varchar(50), totflow varchar(50), has_newcon int2, nconstat numeric(38,8), has_review int2, city varchar(50), state varchar(50), zip varchar(50), geotime timestamp, geouser varchar(50), usersiteid varchar(50), sector varchar(50), fire_dist varchar(50), firefilt varchar(50), m_name varchar(50), m_street_num varchar(50), m_stprefix varchar(50), m_address1 varchar(60), m_sttype varchar(50), m_stsuffix varchar(50), m_address2 varchar(60), m_city varchar(50), m_state varchar(50), m_zip varchar(50), site_stat varchar(50), multiproj int2, faclroutid varchar(50), con_fone varchar(50), con_name varchar(50), con_fax varchar(50),
      busi_type varchar(50), buscomres varchar(50), verloc int2, frresp varchar(50), is_part_of int4, lat_deg varchar(50), long_deg varchar(50), lattitude varchar(50), longitude varchar(50), xc numeric(38,8), yc numeric(38,8), comm_name varchar(50), country varchar(50), has_names numeric(38,8), has_shutof numeric(38,8), has_pplans numeric(38,8), has_hydrants numeric(38,8), has_images numeric(38,8), has_hazmat numeric(38,8), has_hazards numeric(38,8), has_access numeric(38,8), has_tanks numeric(38,8), has_extingui numeric(38,8), has_alarms numeric(38,8), cross_st varchar(50), co_log int2, co_date timestamp, co_notes varchar(255), notes varchar(255), cons_type varchar(50),
      insurcont numeric(38,8), insurstru numeric(38,8), cons_iso varchar(50), fw_log int2, fw_notes varchar(255), roof_type varchar(50), heat_sys varchar(50), air_cond varchar(50), year_bilt int4, stru_add varchar(255), supp_notes varchar(255), oth_water varchar(255), site_type varchar(50), nfpa_use varchar(50), nfpa_occ varchar(50), state_occ varchar(50), occ_load numeric(38,8), permit_req int2, bld_height numeric(38,8), num_storys numeric(38,8), num_rooms numeric(38,8), t_sq_feet numeric(38,8), b_sq_feet numeric(38,8), bld_status varchar(50), basmt_lvls numeric(38,8), basmt_use varchar(50), attic_use varchar(50), f_door_log int2, f_door_typ varchar(50), em_lit_log int2,
      em_lit_num numeric(38,8), fireload varchar(50), uniqdesc varchar(255), stock varchar(50), taxmap_num varchar(50), fire_comp varchar(50), fire_stat varchar(50), f_alrm_log int2, f_alrm_typ varchar(50), secu_type varchar(50), knox_log int2, knox_loc varchar(50), bld_keys_c int2, keys_loc varchar(50), f_exit_log int2, s_detc_log int2, sing_mult varchar(50), permit_num varchar(50), permit_rej int2, permit_comm varchar(255), occ_detail varchar(255), con_first varchar(50), locc_class varchar(50), inspdist varchar(50), loc_seq numeric(15,0), addmark varchar(50), stname varchar(50), m_stname varchar(50), rowguid numeric(38,0), edit_date timestamp,
      edit_by varchar(100)
    -> coagis.coa_knox_box_locations (writer POSTGIS_3)
coagis.coa_knox_box_locations (writer POSTGIS_3)
    attributes: objectid int4,PRIKEY, site_seq numeric(15,0), dept_seq numeric(15,0), oth_seq numeric(15,0), addtime timestamp, adduser varchar(100), site_name varchar(80), modmark varchar(50), mailmlifk numeric(15,0), street_num varchar(50), stprefix varchar(50), address1 varchar(60), sttype varchar(50), stsuffix varchar(50), address2 varchar(60), stinter varchar(5), insp_type varchar(50), insp_freq numeric(38,8), last_insp timestamp, insp_due timestamp, comp_due timestamp, lnoncomply varchar(5), lactive varchar(5), ppreview timestamp, ppreviewer varchar(50), fireflow_ci varchar(50), fireflow_co varchar(50), fireflow_oi varchar(50), fireflow_xi varchar(50), baseflow varchar(50),
      fireflow_si varchar(50), totflow varchar(50), has_newcon varchar(5), nconstat numeric(38,8), has_review varchar(5), city varchar(50), state varchar(50), zip varchar(50), geotime timestamp, geouser varchar(50), usersiteid varchar(50), sector varchar(50), fire_dist varchar(50), firefilt varchar(50), m_name varchar(50), m_street_num varchar(50), m_stprefix varchar(50), m_address1 varchar(60), m_sttype varchar(50), m_stsuffix varchar(50), m_address2 varchar(60), m_city varchar(50), m_state varchar(50), m_zip varchar(50), site_stat varchar(50), multiproj varchar(5), faclroutid varchar(50), con_fone varchar(50), con_name varchar(50), con_fax varchar(50),
      busi_type varchar(50), buscomres varchar(50), verloc varchar(5), frresp varchar(50), is_part_of int4, lat_deg varchar(50), long_deg varchar(50), lattitude varchar(50), longitude varchar(50), xc numeric(38,8), yc numeric(38,8), comm_name varchar(50), country varchar(50), has_names numeric(38,8), has_shutof numeric(38,8), has_pplans numeric(38,8), has_hydrants numeric(38,8), has_images numeric(38,8), has_hazmat numeric(38,8), has_hazards numeric(38,8), has_access numeric(38,8), has_tanks numeric(38,8), has_extingui numeric(38,8), has_alarms numeric(38,8), cross_st varchar(50), co_log varchar(5), co_date timestamp, co_notes varchar(1000), notes varchar(8000), cons_type varchar(50),
      insurcont numeric(38,8), insurstru numeric(38,8), cons_iso varchar(50), fw_log varchar(5), fw_notes varchar(1000), roof_type varchar(50), heat_sys varchar(50), air_cond varchar(50), year_bilt int4, stru_add varchar(1000), supp_notes varchar(1000), oth_water varchar(1000), site_type varchar(50), nfpa_use varchar(50), nfpa_occ varchar(50), state_occ varchar(50), occ_load numeric(38,8), permit_req varchar(5), bld_height numeric(38,8), num_storys numeric(38,8), num_rooms numeric(38,8), t_sq_feet numeric(38,8), b_sq_feet numeric(38,8), bld_status varchar(50), basmt_lvls numeric(38,8), basmt_use varchar(50), attic_use varchar(50), f_door_log varchar(5), f_door_typ varchar(50), em_lit_log varchar(5),
      em_lit_num numeric(38,8), fireload varchar(50), uniqdesc varchar(8000), stock varchar(50), taxmap_num varchar(50), fire_comp varchar(50), fire_stat varchar(50), f_alrm_log varchar(5), f_alrm_typ varchar(50), secu_type varchar(50), knox_log varchar(5), knox_loc varchar(50), bld_keys_c varchar(5), keys_loc varchar(50), f_exit_log varchar(5), s_detc_log varchar(5), sing_mult varchar(50), permit_num varchar(50), permit_rej varchar(5), permit_comm varchar(255), occ_detail varchar(255), con_first varchar(50), locc_class varchar(50), inspdist varchar(50), loc_seq numeric(15,0), addmark varchar(50), stname varchar(50), m_stname varchar(50), rowguid numeric(38,0), edit_date timestamp,
      edit_by varchar(100)
