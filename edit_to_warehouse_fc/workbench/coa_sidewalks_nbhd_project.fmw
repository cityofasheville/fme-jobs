FME workspace coa_sidewalks_nbhd_project.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_sidewalks_nbhd_project (reader POSTGIS_1)
    attributes: objectid int4,PRIKEY, maintenanceentity varchar(150), material varchar(150), narrativecomments varchar(150), coasnowremoval varchar(50), fundrecid varchar(50), segmenttype varchar(50), edit_date timestamp, edit_by varchar(100), streetname varchar(100), assocstmaint varchar(50), projectname varchar(150), locationdescription varchar(250), neighborhoodsidewalk varchar(50), fyconstructed int4, fundingsource varchar(50)
    -> coagis.coa_sidewalks_nbhd_project (writer POSTGIS_2)
coagis.coa_sidewalks_nbhd_project (writer POSTGIS_2)
    attributes: objectid int4, maintenanceentity varchar(150), material varchar(150), narrativecomments varchar(150), coasnowremoval varchar(50), fundrecid varchar(50), segmenttype varchar(50), edit_date timestamp, edit_by varchar(100), streetname varchar(100), assocstmaint varchar(50), projectname varchar(150), locationdescription varchar(250), neighborhoodsidewalk varchar(50), fyconstructed int4, fundingsource varchar(50)
