FME workspace coa_stream_calls.fmw

Parameters:
- SourceDataset_POSTGIS = coa-gis-edit1b   # Connection
- DestDataset_POSTGIS = coa-gis-warehouse1   # Connection

Readers:
- POSTGIS_1: POSTGIS from $(SourceDataset_POSTGIS)

Writers:
- POSTGIS_2: POSTGIS to $(DestDataset_POSTGIS)

coagis.coa_stream_calls (reader POSTGIS_1)
    attributes: objectid int4,PRIKEY, stateguid varchar(38), from_measure numeric(38,8), to_measure numeric(38,8), jurisstream varchar(10), docpath varchar(255), comments varchar(100), date_ timestamp, enabled int2, edit_date timestamp, edit_by varchar(100), stream_type varchar(50), streamcall_agency varchar(50)
    -> MeasureRemover
MeasureRemover
    REMOVE_ALL = Yes
    -> coagis.coa_stream_calls (writer POSTGIS_2)
coagis.coa_stream_calls (writer POSTGIS_2)
    attributes: objectid int4,PRIKEY, stateguid varchar(38), from_measure numeric(38,8), to_measure numeric(38,8), jurisstream varchar(10), docpath varchar(255), comments varchar(100), date_ timestamp, enabled int4, edit_date timestamp, edit_by varchar(100), stream_type varchar(50), streamcall_agency varchar(50)
