FME workspace coa_traffic_calming_measures.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_traffic_calming_measures (reader POSTGIS_1)
    attributes: objectid int4,PRIKEY, trafficcon varchar(20), dateinstal timestamp, locationde varchar(254), linearoffs numeric(38,8), subtypefie int4, segmentid varchar(20), projectnam varchar(254), pointmeasu numeric(38,8), verticalde varchar(254), horizontal int4, angle int2, length int2, width int2, taper int2, radius int2, loc_angle numeric(38,8), edit_date timestamp, edit_by varchar(100)
    -> coagis.coa_traffic_calming_measures (writer POSTGIS_2)
coagis.coa_traffic_calming_measures (writer POSTGIS_2)
    attributes: objectid int4, trafficcon varchar(20), dateinstal timestamp, locationde varchar(254), linearoffs numeric(38,8), subtypefie int4, segmentid varchar(20), projectnam varchar(254), pointmeasu numeric(38,8), verticalde varchar(254), horizontal int4, angle int2, length int2, width int2, taper int2, radius int2, loc_angle numeric(38,8), edit_date timestamp, edit_by varchar(100)
