FME workspace coa_local_historic_landmarks.fmw

Parameters:
- DestDataset_POSTGIS = coa-gis-warehouse1b   # Connection
- SourceDataset_POSTGIS = coa-gis-edit1b   # Connection
- DestDataset_POSTGIS_4 = coa-gis-warehouse1b   # Connection

Readers:
- POSTGIS_1: POSTGIS from $(SourceDataset_POSTGIS)

Writers:
- POSTGIS_2: POSTGIS to $(DestDataset_POSTGIS)
- POSTGIS_3: POSTGIS to $(DestDataset_POSTGIS_4)

coagis.coa_local_historic_landmarks (reader POSTGIS_1)
    attributes: objectid int4,PRIKEY, new_pin varchar(15), id_num int2, ll_name varchar(50), address varchar(50), ordinance varchar(20), eff_date timestamp, notes varchar(80), edit_by varchar(100), edit_date timestamp
    -> coagis.coa_local_historic_landmarks (writer POSTGIS_3)
coagis.coa_local_historic_landmarks (writer POSTGIS_3)
    attributes: objectid int4,PRIKEY, new_pin varchar(15), id_num int2, ll_name varchar(50), address varchar(50), ordinance varchar(20), eff_date timestamp, notes varchar(80), edit_by varchar(100), edit_date timestamp
