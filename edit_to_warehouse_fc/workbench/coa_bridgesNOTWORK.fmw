FME workspace coa_bridgesNOTWORK.fmw

Parameters:
- SourceDataset_POSTGIS = coa-gis-edit1b   # Connection
- DestDataset_POSTGIS = coa-gis-warehouse1   # Connection

Readers:
- POSTGIS_1: POSTGIS from $(SourceDataset_POSTGIS)

Writers:
- POSTGIS_2: POSTGIS to $(DestDataset_POSTGIS)

coagis.coa_bridges (reader POSTGIS_1)
    attributes: objectid int4,PRIKEY, bridge_num varchar(6), bsip_bnum varchar(7), source varchar(50), county varchar(12), route varchar(30), crossover varchar(50), maintained varchar(7), year_built varchar(40), location varchar(75), structype varchar(50), ftr_intrsc varchar(24), f_carried varchar(18), roadway_length varchar(50), crossing_length varchar(50), remaining varchar(50), inventory varchar(50), operating varchar(50), present_condition varchar(50), maintenance varchar(50), on_state_inventory varchar(150), date_last1 varchar(50), date_last_inspected varchar(50), edit_date timestamp, edit_by varchar(100)
    -> MeasureRemover
MeasureRemover
    REMOVE_ALL = Yes
    -> coagis.coa_bridges (writer POSTGIS_2)
coagis.coa_bridges (writer POSTGIS_2)
    attributes: objectid int4,PRIKEY, bridge_num varchar(6), bsip_bnum varchar(7), source varchar(50), county varchar(12), route varchar(30), crossover varchar(50), maintained varchar(7), year_built varchar(40), location varchar(75), structype varchar(50), ftr_intrsc varchar(24), f_carried varchar(18), roadway_length varchar(50), crossing_length varchar(50), remaining varchar(50), inventory varchar(50), operating varchar(50), present_condition varchar(50), maintenance varchar(50), on_state_inventory varchar(150), date_last1 varchar(50), date_last_inspected varchar(50), edit_date timestamp, edit_by varchar(100)
