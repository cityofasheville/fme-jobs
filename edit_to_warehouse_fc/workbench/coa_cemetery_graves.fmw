FME workspace coa_cemetery_graves.fmw

Parameters:
- SourceDataset_POSTGIS = coa-gis-edit1b   # Connection
- DestDataset_POSTGIS = coa-gis-warehouse1b   # Connection
- DestDataset_POSTGIS_4 = coa-gis-warehouse1b   # Connection

Readers:
- POSTGIS_1: POSTGIS from $(SourceDataset_POSTGIS)

Writers:
- POSTGIS_2: POSTGIS to $(DestDataset_POSTGIS)
- POSTGIS_3: POSTGIS to $(DestDataset_POSTGIS_4)

coagis.coa_cbd_development_standard_features (reader POSTGIS_1)
    attributes: objectid int4,PRIKEY, feature_type varchar(50), designation varchar(50), edit_date timestamp, edit_by varchar(100)
coagis.coa_cbd_development_standard_features (writer POSTGIS_2)
    attributes: objectid int4, feature_type varchar(50), designation varchar(50), edit_date timestamp, edit_by varchar(100)
coagis.coa_cemetery_graves (reader POSTGIS_1)
    attributes: objectid int4,PRIKEY, interment_num numeric(38,8), section varchar(50), lot numeric(38,8), grave_num numeric(38,8), last_name varchar(50), first_name varchar(50), middle_name varchar(50), title varchar(50), dob timestamp, dod timestamp, age int4, type varchar(50), military varchar(50), notes varchar(100), photo varchar(150), edit_by varchar(100), edit_date timestamp, url_photo varchar(255), sec_lot_grave varchar(30)
    -> coagis.coa_cemetery_graves (writer POSTGIS_3)
coagis.coa_cemetery_graves (writer POSTGIS_3)
    attributes: objectid int4, interment_num numeric(38,8), section varchar(50), lot numeric(38,8), grave_num numeric(38,8), last_name varchar(50), first_name varchar(50), middle_name varchar(50), title varchar(50), dob timestamp, dod timestamp, age int4, type varchar(50), military varchar(50), notes varchar(100), photo varchar(150), edit_by varchar(100), edit_date timestamp, url_photo varchar(255), sec_lot_grave varchar(30)
