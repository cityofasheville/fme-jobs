FME workspace coa_national_register_properties.fmw

Parameters:
- DestDataset_POSTGIS = coa-gis-warehouse1b   # Connection
- SourceDataset_POSTGIS = coa-gis-edit1b   # Connection
- DestDataset_POSTGIS_4 = coa-gis-warehouse1b   # Connection

Readers:
- POSTGIS_1: POSTGIS from $(SourceDataset_POSTGIS)

Writers:
- POSTGIS_2: POSTGIS to $(DestDataset_POSTGIS)
- POSTGIS_3: POSTGIS to $(DestDataset_POSTGIS_4)

coagis.coa_national_register_properties (reader POSTGIS_1)
    attributes: objectid int4,PRIKEY, id int4, name varchar(50), area_type varchar(20), edit_date timestamp, edit_by varchar(100)
    -> coagis.coa_national_register_properties (writer POSTGIS_3)
coagis.coa_national_register_properties (writer POSTGIS_3)
    attributes: objectid int4,PRIKEY, id int4, name varchar(50), area_type varchar(20), edit_date timestamp, edit_by varchar(100)
