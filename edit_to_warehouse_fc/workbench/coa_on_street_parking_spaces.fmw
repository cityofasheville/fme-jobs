FME workspace coa_on_street_parking_spaces.fmw

Parameters:
- DestDataset_POSTGIS = coa-gis-warehouse1b   # Connection
- SourceDataset_POSTGIS = coa-gis-edit1b   # Connection
- DestDataset_POSTGIS_4 = coa-gis-warehouse1b   # Connection

Readers:
- POSTGIS_1: POSTGIS from $(SourceDataset_POSTGIS)

Writers:
- POSTGIS_2: POSTGIS to $(DestDataset_POSTGIS)
- POSTGIS_3: POSTGIS to $(DestDataset_POSTGIS_4)

coagis.coa_on_street_parking_spaces (reader POSTGIS_1)
    attributes: objectid int4,PRIKEY, id varchar(7), type varchar(150), foreign_key varchar(7), orientation varchar(150), loading_zone int2, comments varchar(50), permit_color varchar(150), subtype varchar(150), edit_date timestamp, edit_by varchar(100)
    -> coagis.coa_on_street_parking_spaces (writer POSTGIS_3)
coagis.coa_on_street_parking_spaces (writer POSTGIS_3)
    attributes: objectid int4,PRIKEY, id varchar(7), type varchar(150), foreign_key varchar(7), orientation varchar(150), loading_zone int4, comments varchar(50), permit_color varchar(150), subtype varchar(150), edit_date timestamp, edit_by varchar(100)
