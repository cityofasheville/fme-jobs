FME workspace coa_water_sample_sites.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_water_sample_sites (reader POSTGIS_1)
    attributes: objectid int4,PRIKEY, field1 int4, unique_code varchar(5), site_name varchar(50), address varchar(50), city varchar(25), january varchar(10), february varchar(10), march varchar(10), april varchar(10), may varchar(10), june varchar(10), july varchar(10), august varchar(10), september varchar(10), october varchar(10), november varchar(10), december varchar(10), zone varchar(30), last_mod_date timestamp, last_mod_by varchar(32), maximo_type varchar(30), maximo_seq_num int4, asset_code varchar(50), mrc varchar(8), wrnty_start timestamp, wrnty_end timestamp, edit_date timestamp, edit_by varchar(100)
    -> coagis.coa_water_sample_sites (writer POSTGIS_2)
coagis.coa_water_sample_sites (writer POSTGIS_2)
    attributes: objectid int4,PRIKEY, field1 int4, unique_code varchar(5), site_name varchar(50), address varchar(50), city varchar(25), january varchar(10), february varchar(10), march varchar(10), april varchar(10), may varchar(10), june varchar(10), july varchar(10), august varchar(10), september varchar(10), october varchar(10), november varchar(10), december varchar(10), zone varchar(30), last_mod_date timestamp, last_mod_by varchar(32), maximo_type varchar(30), maximo_seq_num int4, asset_code varchar(50), mrc varchar(8), wrnty_start timestamp, wrnty_end timestamp, edit_date timestamp, edit_by varchar(100)
