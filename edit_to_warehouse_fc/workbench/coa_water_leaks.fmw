FME workspace coa_water_leaks.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_water_leaks (reader POSTGIS_1)
    attributes: objectid int4,PRIKEY, location varchar(50), observation timestamp, district varchar(150), source varchar(150), workorderid varchar(10), comments varchar(75), status varchar(150), pipesize varchar(150), pipematerial varchar(150), edit_date timestamp, edit_by varchar(100)
    -> coagis.coa_water_leaks (writer POSTGIS_2)
coagis.coa_water_leaks (writer POSTGIS_2)
    attributes: objectid int4,PRIKEY, location varchar(50), observation timestamp, district varchar(150), source varchar(150), workorderid varchar(10), comments varchar(75), status varchar(150), pipesize varchar(150), pipematerial varchar(150), edit_date timestamp, edit_by varchar(100)
