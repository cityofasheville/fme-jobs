FME workspace coa_communication_tower.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_communication_tower (reader POSTGIS_1)
    attributes: objectid int4,PRIKEY, name varchar(50), owner varchar(50), offseta numeric(5,1), offsetb numeric(5,1), azimuth1 int4, azimuth2 int4, vert1 int4, vert2 int4, radius1 int4, radius2 int4, status int2, edit_date timestamp, edit_by varchar(100), towerid varchar(50), latitude numeric(38,8), longitude numeric(38,8), address varchar(100), city varchar(25), state varchar(50), county varchar(150), zip numeric(38,8), classification varchar(50), type varchar(50), height numeric(15,2)
    -> coagis.coa_communication_tower (writer POSTGIS_2)
coagis.coa_communication_tower (writer POSTGIS_2)
    attributes: objectid int4,PRIKEY, name varchar(50), owner varchar(50), offseta numeric(5,1), offsetb numeric(5,1), azimuth1 int4, azimuth2 int4, vert1 int4, vert2 int4, radius1 int4, radius2 int4, status int4, edit_date timestamp, edit_by varchar(100)
