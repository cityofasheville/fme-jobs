FME workspace coa_pedplan_aadt.fmw

Parameters:
- DestDataset_POSTGIS = coa-gis-warehouse1b   # Connection
- SourceDataset_POSTGIS = coa-gis-edit1b   # Connection
- DestDataset_POSTGIS_4 = coa-gis-warehouse1b   # Connection

Readers:
- POSTGIS_1: POSTGIS from $(SourceDataset_POSTGIS)

Writers:
- POSTGIS_2: POSTGIS to $(DestDataset_POSTGIS)
- POSTGIS_3: POSTGIS to $(DestDataset_POSTGIS_4)

coagis.coa_pedplan_aadt (reader POSTGIS_1)
    attributes: objectid int4,PRIKEY, cvrg_vlm_i numeric(38,8), station numeric(38,8), route varchar(254), location varchar(80), x010_aadt numeric(38,8), x009_aadt numeric(38,8), x008_aadt numeric(38,8), x007_aadt numeric(38,8), x006_aadt numeric(38,8), x005_aadt numeric(38,8), x004_aadt numeric(38,8), x003_aadt numeric(38,8), aadt_year int2, aadt numeric(38,8), source varchar(25), st_length_ numeric(38,8), edit_date timestamp, edit_by varchar(100)
    -> coagis.coa_pedplan_aadt (writer POSTGIS_3)
coagis.coa_pedplan_aadt (writer POSTGIS_3)
    attributes: objectid int4,PRIKEY, cvrg_vlm_i numeric(38,8), station numeric(38,8), route varchar(254), location varchar(80), x010_aadt numeric(38,8), x009_aadt numeric(38,8), x008_aadt numeric(38,8), x007_aadt numeric(38,8), x006_aadt numeric(38,8), x005_aadt numeric(38,8), x004_aadt numeric(38,8), x003_aadt numeric(38,8), aadt_year int2, aadt numeric(38,8), source varchar(25), st_length_ numeric(38,8), edit_date timestamp, edit_by varchar(100)
