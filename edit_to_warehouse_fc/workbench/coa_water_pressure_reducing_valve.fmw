FME workspace coa_water_pressure_reducing_valve.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_water_network_structure (reader POSTGIS_1)
    attributes: objectid int4,PRIKEY, facilityid varchar(20), installdate timestamp, locationdescription varchar(200), lifecyclestatus varchar(150), subtype varchar(150), elevation numeric(38,8), networkoid int4, capacity_gallons int4, max_level_feet int2, foot_down_gallons int4, pinnum varchar(16), equipment_cost int4, building_cost int4, name varchar(50), operationalarea varchar(150), source varchar(150), material varchar(150), hyperlink varchar(75), wrnty_start timestamp, wrnty_end timestamp, edit_date timestamp, edit_by varchar(100), latitude numeric(38,8), longitude numeric(38,8), construction_url varchar(255)
    -> coagis.coa_water_network_structure (writer POSTGIS_2)
coagis.coa_water_network_structure (writer POSTGIS_2)
    attributes: objectid int4,PRIKEY, facilityid varchar(20), installdate timestamp, locationdescription varchar(200), lifecyclestatus varchar(150), subtype varchar(150), elevation numeric(38,8), networkoid int4, capacity_gallons int4, max_level_feet int4, foot_down_gallons int4, pinnum varchar(16), equipment_cost int4, building_cost int4, name varchar(50), operationalarea varchar(150), source varchar(150), material varchar(150), hyperlink varchar(75), wrnty_start timestamp, wrnty_end timestamp, edit_date timestamp, edit_by varchar(100), latitude numeric(38,8), longitude numeric(38,8), construction_url varchar(255)
