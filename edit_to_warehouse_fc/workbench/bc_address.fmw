FME workspace bc_address.fmw

Parameters:
- SourceDataset_POSTGIS = coa-gis-edit1b   # Connection
- DestDataset_POSTGIS = coa-gis-warehouse1   # Connection

Readers:
- POSTGIS_1: POSTGIS from $(SourceDataset_POSTGIS)

Writers:
- POSTGIS_2: POSTGIS to $(DestDataset_POSTGIS)

coagis.bc_address (reader POSTGIS_1)
    attributes: objectid int4,PRIKEY, x numeric(38,8), y numeric(38,8), address varchar(40), number int4, apt varchar(4), prefix varchar(2), street_name varchar(30), street_type varchar(4), postdirection varchar(2), civicaddress_id numeric(38,8), location_type int4, change_date timestamp, city varchar(4), zipcode int4, maximo_type varchar(30), maximo_seq_num int4, asset_code varchar(50), mrc varchar(8), pinnum varchar(15), truckday varchar(10), centerline_id numeric(38,8), location_id numeric(38,8), parent_location_id numeric(38,8)
    -> coagis.bc_address (writer POSTGIS_2)
coagis.bc_address (writer POSTGIS_2)
    attributes: objectid int4,PRIKEY, x numeric(38,8), y numeric(38,8), address varchar(40), number int4, apt varchar(4), prefix varchar(2), street_name varchar(30), street_type varchar(4), postdirection varchar(2), civicaddress_id numeric(38,8), location_type int4, change_date timestamp, city varchar(4), zipcode int4, maximo_type varchar(30), maximo_seq_num int4, asset_code varchar(50), mrc varchar(8), pinnum varchar(15), truckday varchar(10), accelaid varchar(25), centerline_id numeric(38,8), location_id numeric(38,8), parent_location_id numeric(38,8)
