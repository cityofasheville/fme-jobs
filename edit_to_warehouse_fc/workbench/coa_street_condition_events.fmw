FME workspace coa_street_condition_events.fmw

Parameters:
- SourceDataset_POSTGIS = coa-gis-edit1b   # Connection
- DestDataset_POSTGIS = coa-gis-warehouse1   # Connection

Readers:
- POSTGIS_1: POSTGIS from $(SourceDataset_POSTGIS)

Writers:
- POSTGIS_2: POSTGIS to $(DestDataset_POSTGIS)

coagis.coa_street_condition_events (reader POSTGIS_1)
    attributes: objectid int4,PRIKEY, centerline numeric(38,8), frommeasure numeric(38,8), tomeasure numeric(38,8), surfacetype varchar(20), noalligatoring int2, lightalligatoring int2, mediumalligatoring int2, severealligatoring int2, cracking int2, rutting int2, oxidation_raveling int2, ridequality int2, patching int2, curbpresence varchar(50), curbtype1 varchar(50), curbtype2 varchar(50), pcs2009 varchar(3), pcr2009 numeric(38,8), editor varchar(2), editdate timestamp, comments varchar(200), currentpcr numeric(38,8), pcrclass varchar(15), pid int4, pcs2009pcr numeric(38,8), pcs2009class text, edit_date timestamp, edit_by varchar(100)
    -> coagis.coa_street_condition_events (writer POSTGIS_2)
coagis.coa_street_condition_events (writer POSTGIS_2)
    attributes: objectid int4,PRIKEY, centerline numeric(38,8), frommeasure numeric(38,8), tomeasure numeric(38,8), surfacetype varchar(20), noalligatoring int4, lightalligatoring int4, mediumalligatoring int4, severealligatoring int4, cracking int4, rutting int4, oxidation_raveling int4, ridequality int4, patching int4, curbpresence varchar(50), curbtype1 varchar(50), curbtype2 varchar(50), pcs2009 varchar(3), pcr2009 numeric(38,8), editor varchar(2), editdate timestamp, comments varchar(200), currentpcr numeric(38,8), pcrclass varchar(15), pid int4, pcs2009pcr numeric(38,8), pcs2009class varchar(1000), edit_date timestamp, edit_by varchar(100)
