FME workspace coa_districts_water.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_districts_water (reader POSTGIS_1)
    attributes: objectid int4,PRIKEY, id numeric(10,0), district varchar(10), mrc varchar(3), edit_date timestamp, edit_by varchar(100)
    -> coagis.coa_districts_water (writer POSTGIS_2)
coagis.coa_districts_water (writer POSTGIS_2)
    attributes: objectid int4,PRIKEY, id numeric(10,0), district varchar(10), mrc varchar(3), edit_date timestamp, edit_by varchar(100)
