FME workspace coa_energy_conservation_areas.fmw

Parameters:
- SourceDataset_POSTGIS = coa-gis-edit1   # Connection
- DestDataset_POSTGIS = coa-gis-warehouse1   # Connection

Readers:
- POSTGIS_1: POSTGIS from $(SourceDataset_POSTGIS)

Writers:
- POSTGIS_2: POSTGIS to $(DestDataset_POSTGIS)

coagis.coa_energy_conservation_locations (reader POSTGIS_1)
    attributes: objectid int4,PRIKEY, pinnum varchar(12), name varchar(254), address varchar(254), estsqft numeric(18,11), dept varchar(254), citydiv varchar(254), edit_date timestamp, edit_by varchar(100)
    -> coagis.coa_energy_conservation_locations (writer POSTGIS_2)
coagis.coa_energy_conservation_locations (writer POSTGIS_2)
    attributes: objectid int4,PRIKEY, pinnum varchar(12), name varchar(254), address varchar(254), estsqft numeric(18,11), dept varchar(254), citydiv varchar(254), edit_date timestamp, edit_by varchar(100)
