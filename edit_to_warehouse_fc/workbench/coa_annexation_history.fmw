FME workspace coa_annexation_history.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_districts_building_safety (reader POSTGIS_1)
    attributes: objectid int4,PRIKEY, areaname varchar(50), edit_date timestamp, edit_by varchar(100)
    -> coagis.coa_districts_building_safety (writer POSTGIS_2)
coagis.coa_districts_building_safety (writer POSTGIS_2)
    attributes: objectid int4,PRIKEY, areaname varchar(50), edit_date timestamp, edit_by varchar(100)
