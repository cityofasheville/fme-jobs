FME workspace coa_districts_sanitation_balance.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_districts_sanitation_balance (reader POSTGIS_1)
    attributes: objectid int4,PRIKEY, jurisdiction varchar(150), label varchar(50), seedname varchar(255), subname varchar(150), edit_date timestamp, edit_by varchar(100)
    -> coagis.coa_districts_sanitation_balance (writer POSTGIS_2)
coagis.coa_districts_sanitation_balance (writer POSTGIS_2)
    attributes: objectid int4, jurisdiction varchar(150), label varchar(50), seedname varchar(255), subname varchar(150), edit_date timestamp, edit_by varchar(100)
