FME workspace MAXIMO2WAREHOUSE_maximo_redline_layer.fmw

Parameters:
- SourceDataset_MSSQL_SPATIAL = maximosde   # Source DATABASE Name
- DestDataset_POSTGIS_3 = coa-gis-warehouse1b   # Connection
- MSSQL_SPATIAL_IN_PASSWORD_MSSQL_SPATIAL =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   # Password

Readers:
- MSSQL_SPATIAL_1: MSSQL_SPATIAL from $(SourceDataset_MSSQL_SPATIAL)

Writers:
- POSTGIS_2: POSTGIS to $(DestDataset_POSTGIS_3)

maximogis.redlinelayer (reader MSSQL_SPATIAL_1)
    attributes: id identity, create_dt datetime, status smallint, priority smallint, xml_data image, create_by varchar(30), modified_dt datetime, modified_by varchar(30), parent_redline_id integer, editor_uname varchar(50), complete_dt datetime, comment_text varchar(1000)
    -> coagis.maximo_redline_layer (writer POSTGIS_2)
coagis.maximo_redline_layer (writer POSTGIS_2)
    attributes: objectid int4,PRIKEY, create_dt timestamp, status int2, priority int2, xml_data bytea, create_by varchar(30), modified_dt timestamp, modified_by varchar(30), parent_redline_id int4, editor_uname varchar(50), complete_dt timestamp, comment_text varchar(1000)
