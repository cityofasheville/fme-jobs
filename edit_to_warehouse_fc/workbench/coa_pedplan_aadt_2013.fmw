FME workspace coa_pedplan_aadt_2013.fmw

Parameters:
- DestDataset_POSTGIS = coa-gis-warehouse1b   # Connection
- SourceDataset_POSTGIS = coa-gis-edit1b   # Connection
- DestDataset_POSTGIS_4 = coa-gis-warehouse1b   # Connection

Readers:
- POSTGIS_1: POSTGIS from $(SourceDataset_POSTGIS)

Writers:
- POSTGIS_2: POSTGIS to $(DestDataset_POSTGIS)
- POSTGIS_3: POSTGIS to $(DestDataset_POSTGIS_4)

coagis.coa_pedplan_aadt_2013 (reader POSTGIS_1)
    attributes: objectid int4,PRIKEY, cvrg_vlm_i numeric(18,5), station numeric(18,5), county varchar(20), route varchar(254), location varchar(80), aadt_2012 int4, aadt_2011 int4, aadt_2010 int4, aadt_2009 int4, aadt_2008 int4, aadt_year int2, aadt int4, source varchar(25), edit_date timestamp, edit_by varchar(100), aadt_2013 int4
    -> coagis.coa_pedplan_aadt_2013 (writer POSTGIS_3)
coagis.coa_pedplan_aadt_2013 (writer POSTGIS_3)
    attributes: objectid int4,PRIKEY, cvrg_vlm_i numeric(18,5), station numeric(18,5), county varchar(20), route varchar(254), location varchar(80), aadt_2012 int4, aadt_2011 int4, aadt_2010 int4, aadt_2009 int4, aadt_2008 int4, aadt_year int2, aadt int4, source varchar(25), edit_date timestamp, edit_by varchar(100), aadt_2013 int4
