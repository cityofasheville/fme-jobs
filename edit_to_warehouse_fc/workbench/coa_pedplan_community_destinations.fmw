FME workspace coa_pedplan_community_destinations.fmw

Parameters:
- DestDataset_POSTGIS = coa-gis-warehouse1b   # Connection
- SourceDataset_POSTGIS = coa-gis-edit1b   # Connection
- DestDataset_POSTGIS_4 = coa-gis-warehouse1b   # Connection

Readers:
- POSTGIS_1: POSTGIS from $(SourceDataset_POSTGIS)

Writers:
- POSTGIS_2: POSTGIS to $(DestDataset_POSTGIS)
- POSTGIS_3: POSTGIS to $(DestDataset_POSTGIS_4)

coagis.coa_pedplan_community_destinations (reader POSTGIS_1)
    attributes: objectid int4,PRIKEY, name varchar(50), type varchar(50), edit_date timestamp, edit_by varchar(100), type2 varchar(50)
    -> coagis.coa_pedplan_community_destinations (writer POSTGIS_3)
coagis.coa_pedplan_community_destinations (writer POSTGIS_3)
    attributes: objectid int4,PRIKEY, name varchar(50), type varchar(50), edit_date timestamp, edit_by varchar(100), type2 varchar(50)
