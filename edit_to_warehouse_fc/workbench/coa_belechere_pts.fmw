FME workspace coa_belechere_pts.fmw

Parameters:
- SourceDataset_POSTGIS = coa-gis-edit1b   # Connection
- DestDataset_POSTGIS = coa-gis-warehouse1   # Connection

Readers:
- POSTGIS_1: POSTGIS from $(SourceDataset_POSTGIS)

Writers:
- POSTGIS_2: POSTGIS to $(DestDataset_POSTGIS)

coagis.coa_belechere_booths (reader POSTGIS_1)
    attributes: objectid int4,PRIKEY, booth_no int2, edit_date timestamp, edit_by varchar(100)
    -> coagis.coa_belechere_booths (writer POSTGIS_2)
coagis.coa_belechere_booths (writer POSTGIS_2)
    attributes: objectid int4,PRIKEY, booth_no int2, edit_date timestamp, edit_by varchar(100)
