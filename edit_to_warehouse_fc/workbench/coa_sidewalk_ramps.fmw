FME workspace coa_sidewalk_ramps.fmw

Parameters:
- SourceDataset_POSTGIS = coa-gis-edit1b   # Connection
- DestDataset_POSTGIS = coa-gis-warehouse1   # Connection

Readers:
- POSTGIS_1: POSTGIS from $(SourceDataset_POSTGIS)

Writers:
- POSTGIS_2: POSTGIS to $(DestDataset_POSTGIS)

coagis.coa_sidewalk_ramps (reader POSTGIS_1)
    attributes: objectid int4,PRIKEY, comp_ varchar(2), edit_date timestamp, edit_by varchar(100), compliant varchar(3), condate timestamp, conby varchar(150), coninfo varchar(50)
    -> coagis.coa_sidewalk_ramps (writer POSTGIS_2)
coagis.coa_sidewalk_ramps (writer POSTGIS_2)
    attributes: objectid int4,PRIKEY, comp_ varchar(2), edit_date timestamp, edit_by varchar(100), conby varchar(150), coninfo varchar(50), condate varchar(10)
