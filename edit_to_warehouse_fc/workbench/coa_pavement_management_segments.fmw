FME workspace coa_pavement_management_segments.fmw

Parameters:
- DestDataset_POSTGIS = coa-gis-warehouse1b   # Connection
- SourceDataset_POSTGIS = coa-gis-edit1b   # Connection
- DestDataset_POSTGIS_4 = coa-gis-warehouse1b   # Connection

Readers:
- POSTGIS_1: POSTGIS from $(SourceDataset_POSTGIS)

Writers:
- POSTGIS_2: POSTGIS to $(DestDataset_POSTGIS)
- POSTGIS_3: POSTGIS to $(DestDataset_POSTGIS_4)

coagis.coa_pavement_management_segments (reader POSTGIS_1)
    attributes: objectid int4,PRIKEY, street_name varchar(30), maintenance_entity varchar(150), current_condition_rank varchar(150), maintenance_needed varchar(150), current_condition_rating int2, paving_material varchar(150), last_paving_activity varchar(150), paving_activity_comments varchar(50), date_of_last_paving_activity timestamp, evaluated_during_pcs_2004 varchar(150), pcs_2004_rank varchar(150), pcs_2004_rating numeric(38,8), pcs_2004_rating_rounded int2, pcs_2004_fielddate timestamp, pcs_2004_comments varchar(50), original_itre_rating_1999 int2, original_itre_id int4, curb_type_1st_side_pcs_2004 varchar(150), curb_type_2nd_side_pcs_2004 varchar(150), curb_left_mat_pre_pcs_2004 varchar(150), curb_right_mat_pre_pcs_2004 varchar(150), sidewalk_1st_side_ref_pointid int2, sidewalk_presence_1st_side varchar(150), sidewalk_condition_1st_side varchar(150), sidewalk_material_1st_side varchar(150), sidewalk_width_1st_side varchar(150), sidewalk_2nd_side_ref_pointid varchar(50), sidewalk_presence_2nd_side varchar(150), sidewalk_condition_2nd_side varchar(150),
      sidewalk_material_2nd_side varchar(150), sidewalk_width_2nd_side varchar(150), sidewalk_comments varchar(50), mph int2, oneway varchar(150), school_zone varchar(150), snow_priority int2, street_name_prefix varchar(2), street_name_2 varchar(30), street_type varchar(2), street_class varchar(2), st_length int4, st_width int2, st_mill varchar(100), sh_width int2, st_totwidth int2, st_lanes int2, st_direction varchar(150), p_cost1 numeric(38,8), p_cost int4, p_org varchar(150), sw_material varchar(150), sw_activity varchar(150), sw_date timestamp, sw_cost int4, sw_rating int2, sw_status varchar(150), sw_width numeric(38,8), sw_org varchar(150), cl_activity varchar(150),
      cl_date timestamp, cl_comments varchar(50), cl_org varchar(150), cl_cost int2, cr_activity varchar(150), cr_date timestamp, cr_org varchar(150), cr_cost int4, cr_comments varchar(50), gasb_st_sy varchar(50), gasb_st_value int4, gasb_sw_sy int4, gasb_sw_value int4, gasb_sw_status int2, gasb_cl_value int4, gasb_cr_value int4, mo varchar(2), yr varchar(2), temp_ varchar(25), geo_id int2, linkid int2, mphord int2, abbr varchar(5), lnmiles int4, p_dbu_type varchar(150), p_dbu_editor varchar(150), p_dbu_date timestamp, sw_dbu_type varchar(150), sw_dbu_editor varchar(150), sw_dbu_date timestamp,
      cg_dbu_type varchar(150), cg_dbu_editor varchar(150), cg_dbu_date timestamp, st_dbu_type varchar(150), st_dbu_editor varchar(150), st_coll_meth varchar(150), st_dbu_date timestamp, pms_an int2, pms_al int2, pms_am int2, pms_as int2, pms_bc varchar(150), pms_ru varchar(150), pms_ra varchar(150), pms_bl varchar(150), pms_rq varchar(150), pms_pa varchar(150), oppositerate int4, run1 int2, testbc int2, testru int2, testra int2, testrq int2, testpa int2, difference int4, pilot int2, objid varchar(20), edit_date timestamp, edit_by varchar(25), sw_symb varchar(30),
      curb_presence varchar(150), sweep varchar(2), sweepdistrict varchar(35), sweeparea varchar(35), sweepday varchar(12), swcompliance varchar(50)
    -> coagis.coa_pavement_management_segments (writer POSTGIS_3)
coagis.coa_pavement_management_segments (writer POSTGIS_3)
    attributes: objectid int4,PRIKEY, street_name varchar(30), maintenance_entity varchar(150), current_condition_rank varchar(150), maintenance_needed varchar(150), current_condition_rating int4, paving_material varchar(150), last_paving_activity varchar(150), paving_activity_comments varchar(50), date_of_last_paving_activity timestamp, evaluated_during_pcs_2004 varchar(150), pcs_2004_rank varchar(150), pcs_2004_rating numeric(38,8), pcs_2004_rating_rounded int4, pcs_2004_fielddate timestamp, pcs_2004_comments varchar(50), original_itre_rating_1999 int4, original_itre_id int4, curb_type_1st_side_pcs_2004 varchar(150), curb_type_2nd_side_pcs_2004 varchar(150), curb_left_mat_pre_pcs_2004 varchar(150), curb_right_mat_pre_pcs_2004 varchar(150), sidewalk_1st_side_ref_pointid int4, sidewalk_presence_1st_side varchar(150), sidewalk_condition_1st_side varchar(150), sidewalk_material_1st_side varchar(150), sidewalk_width_1st_side varchar(150), sidewalk_2nd_side_ref_pointid varchar(50), sidewalk_presence_2nd_side varchar(150), sidewalk_condition_2nd_side varchar(150),
      sidewalk_material_2nd_side varchar(150), sidewalk_width_2nd_side varchar(150), sidewalk_comments varchar(50), mph int4, oneway varchar(150), school_zone varchar(150), snow_priority int4, street_name_prefix varchar(2), street_name_2 varchar(30), street_type varchar(2), street_class varchar(2), st_length int4, st_width int4, st_mill varchar(100), sh_width int4, st_totwidth int4, st_lanes int4, st_direction varchar(150), p_cost1 numeric(38,8), p_cost int4, p_org varchar(150), sw_material varchar(150), sw_activity varchar(150), sw_date timestamp, sw_cost int4, sw_rating int4, sw_status varchar(150), sw_width numeric(38,8), sw_org varchar(150), cl_activity varchar(150),
      cl_date timestamp, cl_comments varchar(50), cl_org varchar(150), cl_cost int4, cr_activity varchar(150), cr_date timestamp, cr_org varchar(150), cr_cost int4, cr_comments varchar(50), gasb_st_sy varchar(50), gasb_st_value int4, gasb_sw_sy int4, gasb_sw_value int4, gasb_sw_status int4, gasb_cl_value int4, gasb_cr_value int4, mo varchar(2), yr varchar(2), temp_ varchar(25), geo_id int4, linkid int4, mphord int4, abbr varchar(5), lnmiles int4, p_dbu_type varchar(150), p_dbu_editor varchar(150), p_dbu_date timestamp, sw_dbu_type varchar(150), sw_dbu_editor varchar(150), sw_dbu_date timestamp,
      cg_dbu_type varchar(150), cg_dbu_editor varchar(150), cg_dbu_date timestamp, st_dbu_type varchar(150), st_dbu_editor varchar(150), st_coll_meth varchar(150), st_dbu_date timestamp, pms_an int4, pms_al int4, pms_am int4, pms_as int4, pms_bc varchar(150), pms_ru varchar(150), pms_ra varchar(150), pms_bl varchar(150), pms_rq varchar(150), pms_pa varchar(150), oppositerate int4, run1 int4, testbc int4, testru int4, testra int4, testrq int4, testpa int4, difference int4, pilot int4, objid varchar(20), edit_date timestamp, edit_by varchar(25), sw_symb varchar(30),
      curb_presence varchar(150), sweep varchar(2), sweepdistrict varchar(35), sweeparea varchar(35), sweepday varchar(12), swcompliance varchar(50)
