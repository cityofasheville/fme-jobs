FME workspace coa_water_flow_monitor.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_water_flow_monitor (reader POSTGIS_1)
    attributes: objectid int4,PRIKEY, type varchar(12), installationdate timestamp, location varchar(50), portable varchar(150), edit_date timestamp, edit_by varchar(100)
    -> coagis.coa_water_flow_monitor (writer POSTGIS_2)
coagis.coa_water_flow_monitor (writer POSTGIS_2)
    attributes: objectid int4,PRIKEY, type varchar(12), installationdate timestamp, location varchar(50), portable varchar(150), edit_date timestamp, edit_by varchar(100)
