FME workspace coa_traffic_counts.fmw

Parameters:
- SourceDataset_POSTGIS = coa-gis-edit1b   # Connection
- DestDataset_POSTGIS = coa-gis-warehouse1b   # Connection

Readers:
- POSTGIS_1: POSTGIS from $(SourceDataset_POSTGIS)

Writers:
- POSTGIS_2: POSTGIS to $(DestDataset_POSTGIS)

coagis.coa_traffic_counts (reader POSTGIS_1)
    attributes: objectid int4,PRIKEY, station numeric(38,8), location varchar(80), source varchar(25), traffic_count int4, count_year int2, street_name varchar(254), centerline_id numeric(38,8), edit_date timestamp, edit_by varchar(100)
    -> coagis.coa_traffic_counts (writer POSTGIS_2)
coagis.coa_traffic_counts (writer POSTGIS_2)
    attributes: objectid int4,PRIKEY, station numeric(38,8), location varchar(80), source varchar(25), traffic_count int4, count_year int2, street_name varchar(254), centerline_id numeric(38,8), edit_date timestamp, edit_by varchar(100)
