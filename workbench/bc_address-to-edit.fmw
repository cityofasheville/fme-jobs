FME workspace bc_address-to-edit.fmw

Parameters:
- GEODB_CONFIG_KEYWORD = PG_GEOMETRY   # Configuration Keyword
- bunco-addr-sde = C:\Users\mssqlgisadmin\AppData\Roaming\ESRI\Desktop10.2\ArcCatalog\bcgis-addr.sde   # Connection File
- coa-edit-sde = C:\Users\mssqlgisadmin\AppData\Roaming\ESRI\Desktop10.2\ArcCatalog\coa-gis-edit1.sde   # Connection File

Readers:
- GEODATABASE_SDE_1: GEODATABASE_SDE

Writers:
- GEODATABASE_SDE_2: GEODATABASE_SDE

DBO.COAPOINTVIEW (reader GEODATABASE_SDE_1)
    attributes: x double, y double, address char(40), number integer, apt char(4), prefix char(2), street_name char(30), street_type char(4), postdirection char(2), civicaddress_id double, location_type integer, change_date date, city char(4), zipcode integer, centerline_id double, location_id double, parent_location_id double, OBJECTID integer
    -> coagis.bc_address (writer GEODATABASE_SDE_2)
coagis.bc_address (writer GEODATABASE_SDE_2)
    attributes: objectid integer, x double, y double, address char(40), number integer, apt char(4), prefix char(2), street_name char(30), street_type char(4), postdirection char(2), civicaddress_id double, location_type integer, change_date date, city char(4), zipcode integer, maximo_type char(30), maximo_seq_num integer, asset_code char(50), mrc char(8), pinnum char(15), truckday char(10), centerline_id double, location_id double, parent_location_id double
