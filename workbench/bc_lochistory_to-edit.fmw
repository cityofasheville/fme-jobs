FME workspace bc_lochistory_to-edit.fmw

Parameters:
- bunco-addr-sde = C:\Users\mssqlgisadmin\AppData\Roaming\ESRI\Desktop10.2\ArcCatalog\bcgis-addr.sde   # Connection File
- coa-gis-warehouse1 = coa-gis-warehouse1   # Connection

Readers:
- GEODATABASE_SDE_1: GEODATABASE_SDE

Writers:
- POSTGIS_1: POSTGIS to $(coa-gis-warehouse1)

DBO.location_history (reader GEODATABASE_SDE_1)
    attributes: OBJECTID integer, LOCATION_ID double, LOCATIONTYPE integer, CIVICADDRESS_ID double, PARENT_LOCATION_ID double, BUILDING_ID double, CENTERLINE_ID double, USER_ID char(8), ESN smallint, X_COORD double, Y_COORD double, COMMCODE char(4), STREET_NUMBER integer, UNIT char(4), UNIT_TYPE integer, STREET_PREFIX char(2), STREET_NAME char(30), STREET_TYPE char(4), STREET_POSTDIRECTION char(2), FULL_CIVIC_ADDRESS char(40), POSTAL_CODE integer, CREATE_DATE date, CHANGE_DATE date, PRIMARY_STRUCTURE smallint, STREET_DUPE char(3), PARCEL_ID char(10), PINEXT char(5)
    -> CREATE_DATE2
CREATE_DATE2: DateFormatter
    FMT = FME Date/Time (%Y%m%d%H%M%S)
    SRCFMT = Unknown - Automatic Detection
    INVALID_DATE_VALUE = _FME_NO_OP_
    DATE_ATTR = CREATE_DATE
    -> coagis.bc_address_location_history (writer POSTGIS_1)
coagis.bc_address_location_history (writer POSTGIS_1)
    attributes: objectid int4, location_id numeric(38,8), locationtype int4, civicaddress_id numeric(38,8), parent_location_id numeric(38,8), building_id numeric(38,8), centerline_id numeric(38,8), user_id varchar(8), esn int2, x_coord numeric(38,8), y_coord numeric(38,8), commcode varchar(4), street_number int4, unit varchar(4), unit_type int4, street_prefix varchar(2), street_name varchar(30), street_type varchar(4), street_postdirection varchar(2), full_civic_address varchar(40), postal_code int4, create_date timestamp, change_date timestamp, primary_structure int2, street_dupe varchar(3), parcel_id varchar(10), pinext varchar(5)
