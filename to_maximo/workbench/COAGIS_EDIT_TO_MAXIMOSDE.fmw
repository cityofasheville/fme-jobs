FME workspace COAGIS_EDIT_TO_MAXIMOSDE.fmw

Parameters:
- SourceDataset_POSTGIS = coa-gis-edit1b   # Connection

Readers:
- POSTGIS_1: POSTGIS from $(SourceDataset_POSTGIS)

Writers:
- GEODATABASE_SDE_1: GEODATABASE_SDE

coagis.coa_water_underground_enclosure (reader POSTGIS_1)
    attributes: objectid int4,PRIKEY, facilityid varchar(20), installdate timestamp, subtype varchar(100), workorderid varchar(20), elevation numeric(38,8), covermaterial varchar(150), covertype varchar(20), depth numeric(38,8), invertelevation numeric(38,8), operationalarea varchar(150), lifecyclestatus varchar(150), locationdescription varchar(75), last_mod_date timestamp, last_mod_by varchar(32), maximo_type varchar(30), maximo_seq_num int4, asset_code varchar(50), mrc varchar(8), edit_date timestamp, edit_by varchar(100)
    -> AttributeFilter_4
AttributeFilter_4
    ATTR_NAME = maximo_seq_num
    ATTR_VALUES = <BLANK>,<UNFILTERED>,1
    <UNFILTERED> -> AttributeCreator
AttributeCreator
    ATTR_LIST = mxsiteid,COAWTR,mxcreationstate,1
    -> StringConcatenator_8
StringConcatenator_8
    PARM_LINE = @Value(maximo_type)@Value(maximo_seq_num)
    VAL_ATTR = mxassetnum
    -> MAXIMOGIS.TEMP_UNDERGROUND_ENCLOSURE (writer GEODATABASE_SDE_1)
MAXIMOGIS.TEMP_UNDERGROUND_ENCLOSURE (writer GEODATABASE_SDE_1)
    attributes: OBJECTID integer, FACILITYID char(20), INSTALLDATE date, SUBTYPE char(100), WORKORDERID char(20), ELEVATION double, COVERMATERIAL char(150), COVERTYPE char(20), DEPTH double, INVERTELEVATION double, OPERATIONALAREA char(150), LIFECYCLESTATUS char(150), LOCATIONDESCRIPTION char(75), MXASSETNUM char(20), MRC char(8), EDIT_DATE date, EDIT_BY char(100), mxsiteid char(8), SHAPE.STArea() double, SHAPE.STLength() double
coagis.coa_water_system_valve (reader POSTGIS_1)
    attributes: objectid int4,PRIKEY, facilityid varchar(20), installdate timestamp, workorderid varchar(20), elevation numeric(38,8), bypassvalve varchar(150), directiontoclose varchar(150), currentlyopen varchar(150), motorized varchar(150), normallyopen varchar(150), turnstoclose int2, valvesize varchar(150), locationdescription varchar(50), operationalarea varchar(150), lifecyclestatus varchar(150), source varchar(150), oldwaterdepartment int4, valvetype varchar(150), subtype varchar(150), last_mod_date timestamp, last_mod_by varchar(32), maximo_type varchar(30), maximo_seq_num int4, asset_code varchar(50), mrc varchar(8), edit_date timestamp, edit_by varchar(100), notes varchar(50), criticality_rating int4, physical_location varchar(255)
    -> AttributeFilter_2
AttributeFilter_2
    ATTR_NAME = maximo_seq_num
    ATTR_VALUES = <BLANK>,<UNFILTERED>,1
    <UNFILTERED> -> AttributeCreator_2
AttributeCreator_2
    ATTR_LIST = mxsiteid,COAWTR,mxcreationstate,1
    -> StringConcatenator_7
StringConcatenator_7
    PARM_LINE = @Value(maximo_type)@Value(maximo_seq_num)
    VAL_ATTR = mxassetnum
    -> MAXIMOGIS.TEMP_SYSTEM_VALVE (writer GEODATABASE_SDE_1)
MAXIMOGIS.TEMP_SYSTEM_VALVE (writer GEODATABASE_SDE_1)
    attributes: OBJECTID integer, FACILITYID char(20), INSTALLDATE date, WORKORDERID char(20), ELEVATION double, BYPASSVALVE char(150), DIRECTIONTOCLOSE char(150), CURRENTLYOPEN char(150), MOTORIZED char(150), NORMALLYOPEN char(150), TURNSTOCLOSE smallint, VALVESIZE char(150), LOCATIONDESCRIPTION char(50), OPERATIONALAREA char(150), LIFECYCLESTATUS char(150), SOURCE char(150), OLDWATERDEPARTMENT integer, VALVETYPE char(150), SUBTYPE char(150), MXASSETNUM char(20), MRC char(8), EDIT_DATE date, EDIT_BY char(100), mxsiteid char(8), mxcreationstate smallint, mxassetuid integer
coagis.coa_water_lateral_line (reader POSTGIS_1)
    attributes: objectid int4,PRIKEY, facilityid varchar(20), installdate timestamp, lifecyclestatus varchar(150), subtype varchar(150), workorderid varchar(20), renewaldate timestamp, locationdescription varchar(50), material varchar(150), diameter varchar(150), last_mod_date timestamp, last_mod_by varchar(32), maximo_type varchar(30), maximo_seq_num int4, asset_code varchar(50), mrc varchar(8), edit_date timestamp, edit_by varchar(100), line_type varchar(50)
    -> AttributeFilter_3
AttributeFilter_3
    ATTR_NAME = maximo_seq_num
    ATTR_VALUES = <BLANK>,<UNFILTERED>,1
    <UNFILTERED> -> AttributeCreator_3
AttributeCreator_3
    ATTR_LIST = mxsiteid,COAWTR,mxcreationstate,1
    -> StringConcatenator_6
StringConcatenator_6
    PARM_LINE = @Value(maximo_type)@Value(maximo_seq_num)
    VAL_ATTR = mxassetnum
    -> MAXIMOGIS.TEMP_LATERAL_LINE (writer GEODATABASE_SDE_1)
MAXIMOGIS.TEMP_LATERAL_LINE (writer GEODATABASE_SDE_1)
    attributes: OBJECTID integer, FACILITYID char(20), INSTALLDATE date, LIFECYCLESTATUS char(150), SUBTYPE char(150), WORKORDERID char(20), RENEWALDATE date, LOCATIONDESCRIPTION char(50), MATERIAL char(150), DIAMETER char(150), MXASSETNUM char(20), MRC char(8), EDIT_DATE date, EDIT_BY char(100), mxsiteid char(8), SHAPE.STLength() double
coagis.bc_street (reader POSTGIS_1)
    attributes: objectid int4,PRIKEY, centerline_id numeric(38,8), road_class int4, street_prefix varchar(2), street_name varchar(30), street_type varchar(4), street_postdirection varchar(2), street_dupe varchar(1), full_street_name varchar(32), speed_limit int4, lane_count int4, left_from_address int4, left_to_address int4, right_from_address int4, right_to_address int4, user_id varchar(8), create_date timestamp, change_date timestamp, lesn int2, resn int2, lzip int4, rzip int4, lcommcode varchar(4), rcommcode varchar(4), route_id varchar(20), maximo_type varchar(30), maximo_seq_num int4, asset_code varchar(50), mrc varchar(8), min_range int4,
      max_range int4
    -> AttributeFilter_5
AttributeFilter_5
    ATTR_NAME = maximo_seq_num
    ATTR_VALUES = <BLANK>,<UNFILTERED>,1
    <UNFILTERED> -> AttributeCreator_5
AttributeCreator_5
    ATTR_LIST = mxsiteid,COAWTR
    -> StringConcatenator
StringConcatenator
    PARM_LINE = @Value(maximo_type)@Value(centerline_id)
    VAL_ATTR = mxassetnum
    -> MAXIMOGIS.TEMP_BC_STREET (writer GEODATABASE_SDE_1)
MAXIMOGIS.TEMP_BC_STREET (writer GEODATABASE_SDE_1)
    attributes: OBJECTID integer, CENTERLINE_ID double, ROAD_CLASS integer, STREET_PREFIX char(2), STREET_NAME char(30), STREET_TYPE char(4), STREET_POSTDIRECTION char(2), STREET_DUPE char(1), FULL_STREET_NAME char(32), SPEED_LIMIT integer, LANE_COUNT integer, LEFT_FROM_ADDRESS integer, LEFT_TO_ADDRESS integer, RIGHT_FROM_ADDRESS integer, RIGHT_TO_ADDRESS integer, USER_ID char(8), CREATE_DATE date, CHANGE_DATE date, LESN smallint, RESN smallint, LZIP integer, RZIP integer, LCOMMCODE char(4), RCOMMCODE char(4), ROUTE_ID char(20), MXASSETNUM char(20), MRC char(8), MIN_RANGE integer, MAX_RANGE integer, mxsiteid char(8),
      SHAPE.STLength() double
coagis.bc_address (reader POSTGIS_1)
    attributes: objectid int4,PRIKEY, x numeric(38,8), y numeric(38,8), address varchar(40), number int4, apt varchar(4), prefix varchar(2), street_name varchar(30), street_type varchar(4), postdirection varchar(2), civicaddress_id numeric(38,8), location_type int4, change_date timestamp, city varchar(4), zipcode int4, maximo_type varchar(30), maximo_seq_num int4, asset_code varchar(50), mrc varchar(8), pinnum varchar(15), truckday varchar(10), centerline_id numeric(38,8), location_id numeric(38,8), parent_location_id numeric(38,8)
    -> AttributeFilter_6
AttributeFilter_6
    ATTR_NAME = maximo_seq_num
    ATTR_VALUES = <BLANK>,<UNFILTERED>,1
    <UNFILTERED> -> AttributeCreator_6
AttributeCreator_6
    ATTR_LIST = mxsiteid,COAWTR
    -> StringConcatenator_2
StringConcatenator_2
    PARM_LINE = @Value(maximo_type)@Value(civicaddress_id)
    VAL_ATTR = mxassetnum
    -> MAXIMOGIS.TEMP_BC_ADDRESS (writer GEODATABASE_SDE_1)
MAXIMOGIS.TEMP_BC_ADDRESS (writer GEODATABASE_SDE_1)
    attributes: OBJECTID integer, X double, Y double, ADDRESS char(40), NUMBER integer, APT char(4), PREFIX char(2), STREET_NAME char(30), STREET_TYPE char(4), POSTDIRECTION char(2), CIVICADDRESS_ID double, LOCATION_TYPE integer, CHANGE_DATE date, CITY char(4), ZIPCODE integer, MXADDRESSCODE char(20), MRC char(8), PINNUM char(15), TRUCKDAY char(10), mxsiteid char(8)
coagis.coa_water_sample_sites (reader POSTGIS_1)
    attributes: objectid int4,PRIKEY, field1 int4, unique_code varchar(5), site_name varchar(50), address varchar(50), city varchar(25), january varchar(10), february varchar(10), march varchar(10), april varchar(10), may varchar(10), june varchar(10), july varchar(10), august varchar(10), september varchar(10), october varchar(10), november varchar(10), december varchar(10), zone varchar(30), last_mod_date timestamp, last_mod_by varchar(32), maximo_type varchar(30), maximo_seq_num int4, asset_code varchar(50), mrc varchar(8), wrnty_start timestamp, wrnty_end timestamp, edit_date timestamp, edit_by varchar(100)
    -> AttributeFilter_7
AttributeFilter_7
    ATTR_NAME = maximo_seq_num
    ATTR_VALUES = <BLANK>,<UNFILTERED>,1
    <UNFILTERED> -> AttributeCreator_7
AttributeCreator_7
    ATTR_LIST = mxsiteid,COAWTR
    -> StringConcatenator_3
StringConcatenator_3
    PARM_LINE = @Value(maximo_type)@Value(unique_code)
    VAL_ATTR = assetcode_calc
    -> MAXIMOGIS.TEMP_SAMPLE_SITES (writer GEODATABASE_SDE_1)
MAXIMOGIS.TEMP_SAMPLE_SITES (writer GEODATABASE_SDE_1)
    attributes: OBJECTID integer, FIELD1 integer, UNIQUE_CODE char(5), SITE_NAME char(50), ADDRESS char(50), CITY char(25), JANUARY char(10), FEBRUARY char(10), MARCH char(10), APRIL char(10), MAY char(10), JUNE char(10), JULY char(10), AUGUST char(10), SEPTEMBER char(10), OCTOBER char(10), NOVEMBER char(10), DECEMBER char(10), ZONE char(30), MXASSETNUM char(20), MRC char(8), WRNTY_START date, WRNTY_END date, EDIT_DATE date, EDIT_BY char(100), mxsiteid char(8)
coagis.coa_water_hydrant (reader POSTGIS_1)
    attributes: objectid int4,PRIKEY, facilityid varchar(20), installdate timestamp, lifecyclestatus varchar(150), workorderid varchar(20), elevation numeric(38,8), source varchar(150), oldwaterdepartment int4, operationalarea varchar(150), locationdescription varchar(50), maindiameter varchar(150), last_mod_date timestamp, last_mod_by varchar(32), maximo_type varchar(30), maximo_seq_num int4, asset_code varchar(50), mrc varchar(8), agency varchar(150), edit_date timestamp, edit_by varchar(100), houseno int2, streetname varchar(35), hydrantmake varchar(25), hydrantmodel varchar(50), hydrantyear int2, valvepresent varchar(3), district varchar(3), bonnetcolor varchar(3), hydrant_type varchar(50), date_removed timestamp
    -> AttributeFilter_8
AttributeFilter_8
    ATTR_NAME = maximo_seq_num
    ATTR_VALUES = <BLANK>,<UNFILTERED>,1
    <UNFILTERED> -> AttributeCreator_8
AttributeCreator_8
    ATTR_LIST = mxsiteid,COAWTR
    -> StringConcatenator_4
StringConcatenator_4
    PARM_LINE = @Value(maximo_type)@Value(maximo_seq_num)
    VAL_ATTR = mxassetnum
    -> MAXIMOGIS.TEMP_HYDRANT (writer GEODATABASE_SDE_1)
MAXIMOGIS.TEMP_HYDRANT (writer GEODATABASE_SDE_1)
    attributes: OBJECTID integer, FACILITYID char(20), INSTALLDATE date, LIFECYCLESTATUS char(150), WORKORDERID char(20), ELEVATION double, SOURCE char(150), OLDWATERDEPARTMENT integer, OPERATIONALAREA char(150), LOCATIONDESCRIPTION char(50), MAINDIAMETER char(150), MXASSETNUM char(20), MRC char(8), AGENCY char(150), EDIT_DATE date, EDIT_BY char(100), mxsiteid char(8), hydrant_type char(50)
coagis.coa_water_control_valve (reader POSTGIS_1)
    attributes: objectid int4,PRIKEY, facilityid varchar(20), installdate timestamp, locationdescription varchar(200), lifecyclestatus varchar(150), subtype varchar(150), workorderid varchar(20), elevation numeric(38,8), operationalarea varchar(150), source varchar(150), diameter varchar(150), last_mod_date timestamp, last_mod_by varchar(32), maximo_type varchar(30), maximo_seq_num int4, asset_code varchar(50), mrc varchar(8), edit_date timestamp, edit_by varchar(100)
    -> AttributeFilter_9
AttributeFilter_9
    ATTR_NAME = maximo_seq_num
    ATTR_VALUES = <BLANK>,<UNFILTERED>,1
    <UNFILTERED> -> AttributeCreator_4
AttributeCreator_4
    ATTR_LIST = mxsiteid,COAWTR
    -> StringConcatenator_5
StringConcatenator_5
    PARM_LINE = @Value(maximo_type)@Value(maximo_seq_num)
    VAL_ATTR = mxassetnum
    -> MAXIMOGIS.TEMP_CONTROL_VALVE (writer GEODATABASE_SDE_1)
MAXIMOGIS.TEMP_CONTROL_VALVE (writer GEODATABASE_SDE_1)
    attributes: OBJECTID integer, FACILITYID char(20), INSTALLDATE date, LOCATIONDESCRIPTION char(200), LIFECYCLESTATUS char(150), SUBTYPE char(150), WORKORDERID char(20), ELEVATION double, OPERATIONALAREA char(150), SOURCE char(150), DIAMETER char(150), MXASSETNUM char(20), MRC char(8), EDIT_DATE date, EDIT_BY char(100), mxsiteid char(8)
coagis.coa_water_gravity_main (reader POSTGIS_1)
    attributes: objectid int4,PRIKEY, facilityid varchar(20), installdate timestamp, lifecyclestatus varchar(150), workorderid varchar(20), slope numeric(38,8), material varchar(150), source varchar(150), operationalarea varchar(150), diameter varchar(150), last_mod_date timestamp, last_mod_by varchar(32), maximo_type varchar(30), maximo_seq_num int4, asset_code varchar(50), mrc varchar(8), wrnty_start timestamp, wrnty_end timestamp, edit_date timestamp, edit_by varchar(100), positional_confidence int2, date_aband timestamp
    -> AttributeFilter_10
AttributeFilter_10
    ATTR_NAME = maximo_seq_num
    ATTR_VALUES = <BLANK>,<UNFILTERED>,1
    <UNFILTERED> -> AttributeCreator_9
AttributeCreator_9
    ATTR_LIST = mxsiteid,COAWTR
    -> AttributeValueMapper
AttributeValueMapper
    LUT = 1/2",0.5,3/4",0.75,1",1.0,1 1/4",1.25,1 1/2",1.5,2",2,2 1/2",2.5,3",3,4",4,6",6,8",8,10",10,12",12,14",14,16",16,18",18,20",20,22",22,24",24,26",26,28",28,30",30,32",32,34",34,36",36,38",38,40",40
    SRC = diameter
    VAL_ATTR = DIAMETERINT
    DIRECTION = Forward (Source To Destination)
    -> StringConcatenator_9
StringConcatenator_9
    PARM_LINE = @Value(maximo_type)@Value(maximo_seq_num)
    VAL_ATTR = mxassetnum
    -> MAXIMOGIS.TEMP_GRAVITY_MAIN (writer GEODATABASE_SDE_1)
MAXIMOGIS.TEMP_GRAVITY_MAIN (writer GEODATABASE_SDE_1)
    attributes: OBJECTID integer, FACILITYID char(20), INSTALLDATE date, LIFECYCLESTATUS char(150), WORKORDERID char(20), SLOPE double, MATERIAL char(150), SOURCE char(150), OPERATIONALAREA char(150), DIAMETER char(150), MXASSETNUM char(20), MRC char(8), WRNTY_START date, WRNTY_END date, EDIT_DATE date, EDIT_BY char(100), DIAMETERINT double, mxsiteid char(8), SHAPE.STLength() double
coagis.coa_water_flushing_points (reader POSTGIS_1)
    attributes: objectid int4,PRIKEY, address varchar(150), setting varchar(150), type varchar(150), plant varchar(50), last_mod_date timestamp, last_mod_by varchar(32), maximo_type varchar(30), maximo_seq_num int4, asset_code varchar(50), mrc varchar(8), edit_date timestamp, edit_by varchar(100)
    -> AttributeFilter_11
AttributeFilter_11
    ATTR_NAME = maximo_seq_num
    ATTR_VALUES = <BLANK>,<UNFILTERED>,1
    <UNFILTERED> -> AttributeCreator_10
AttributeCreator_10
    ATTR_LIST = mxsiteid,COAWTR
    -> StringConcatenator_10
StringConcatenator_10
    PARM_LINE = @Value(maximo_type)@Value(maximo_seq_num)
    VAL_ATTR = mxassetnum
    -> MAXIMOGIS.TEMP_WATER_FLUSHING_POINTS (writer GEODATABASE_SDE_1)
MAXIMOGIS.TEMP_WATER_FLUSHING_POINTS (writer GEODATABASE_SDE_1)
    attributes: OBJECTID integer, ADDRESS char(150), SETTING char(150), TYPE char(150), PLANT char(50), LAST_MOD_DATE date, LAST_MOD_BY char(32), MAXIMO_TYPE char(30), MAXIMO_SEQ_NUM integer, ASSET_CODE char(50), MRC char(8), EDIT_DATE date, EDIT_BY char(100), MXASSETNUM char(20), mxsiteid char(8)
