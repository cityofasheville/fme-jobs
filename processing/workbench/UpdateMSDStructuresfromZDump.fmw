FME workspace UpdateMSDStructuresfromZDump.fmw

Parameters:
- SourceDataset_SHAPE = \\coa-backup\gisdata\Engineering\ZDump\MSDUpdate\msdstructuresnad83.shp   # Source ESRI Shape File(s)
- DestDataset_POSTGIS = coagiswarehouse   # Destination PostGIS database
- DestDataset_POSTGIS_3 = coa-gis-warehouse1b   # Connection

Readers:
- SHAPE_1: SHAPE from $(SourceDataset_SHAPE)

Writers:
- POSTGIS_1: POSTGIS to $(DestDataset_POSTGIS)
- POSTGIS_2: POSTGIS to $(DestDataset_POSTGIS_3)

msdstructuresnad83 (reader SHAPE_1)
    attributes: PRJ_NUM char(9), NORTH number(31,11), EAST number(31,11), TELEV number(31,11), INV_DEPTH number(31,11), INVOUT number(31,11), INFO_DATE date, DATASOURCE char(75), SURVEYED number(4,0), MHCOMMENTS char(36), MHMAT char(12), GEOMETRY char(50), STEPS number(4,0), COVER_HOLE number(31,11), INV char(12), NCDNR_INSP number(4,0), INFO_ACC_H number(31,11), INFO_ACC_V number(31,11), SUBTYPE number(4,0), OWNER number(4,0), LINED number(4,0), ENABLED number(4,0), LASTUPDATE date, EDITOR char(50), QA char(10), MHNO number(9,0), ANCILLARYR number(4,0), REPLACED number(4,0), WATERLINE number(4,0), ACTIONTAKE char(50),
      CONDATE date, ELEVASS number(31,11), ELEVSOURCE char(25), MODEL char(10), TELEVASS number(31,11), TELEVSOURC char(25)
    -> Counter
Counter
    CNT_ATTR = objectid
    START = 1
    DOMAIN = counter
    SCOPE = Global
    -> coagis.msd_structures (writer POSTGIS_2)
coagis.msd_structures (writer POSTGIS_2)
    attributes: objectid int4,PRIKEY, prj_num varchar(9), north numeric(19,11), east numeric(19,11), telev numeric(19,11), inv_depth numeric(19,11), invout numeric(19,11), info_date timestamp, datasource varchar(75), surveyed int4, mhcomments varchar(36), mhmat varchar(12), geometry varchar(50), steps int4, cover_hole numeric(19,11), inv varchar(12), ncdnr_insp int4, info_acc_h numeric(19,11), info_acc_v numeric(19,11), subtype int4, owner int4, lined int4, enabled int4, lastupdate timestamp, editor varchar(50), qa varchar(10), mhno int4, ancillaryr int4, replaced int4, waterline int4,
      actiontake varchar(50), condate timestamp, elevass numeric(19,11), elevsource varchar(25), model varchar(10), televass numeric(19,11), televsourc varchar(25)
