FME workspace COMBINING_CONDITIONSTREETSOURCES.fmw

Parameters:
- SourceDataset_POSTGIS = coa-gis-edit1   # Connection
- SourceDataset_POSTGRES = coa-gis-edit1b   # Connection
- DestDataset_POSTGIS = coa-gis-edit1b   # Connection

Readers:
- POSTGIS_1: POSTGIS from $(SourceDataset_POSTGIS)
- POSTGRES_1: POSTGRES from $(SourceDataset_POSTGRES)

Writers:
- POSTGIS_2: POSTGIS to $(DestDataset_POSTGIS)

coagis.coa_street_condition_events (reader POSTGIS_1)
    attributes: objectid int4,PRIKEY, centerline numeric(38,8), frommeasure numeric(38,8), tomeasure numeric(38,8), surfacetype varchar(20), noalligatoring int2, lightalligatoring int2, mediumalligatoring int2, severealligatoring int2, cracking int2, rutting int2, oxidation_raveling int2, ridequality int2, patching int2, curbpresence varchar(50), curbtype1 varchar(50), curbtype2 varchar(50), pcs2009 varchar(3), pcr2009 numeric(38,8), editor varchar(2), editdate timestamp, comments varchar(200), currentpcr numeric(38,8), pcrclass varchar(15), pid int4, pcs2009pcr numeric(38,8), pcs2009class text, edit_date timestamp, edit_by varchar(100)
    -> FeatureMerger_2 [input 1]
coagis.bc_street (reader POSTGIS_1)
    attributes: objectid int4,PRIKEY, centerline_id numeric(38,8), road_class int4, street_prefix varchar(2), street_name varchar(30), street_type varchar(4), street_postdirection varchar(2), street_dupe varchar(1), full_street_name varchar(32), speed_limit int4, lane_count int4, left_from_address int4, left_to_address int4, right_from_address int4, right_to_address int4, user_id varchar(8), create_date timestamp, change_date timestamp, lesn int2, resn int2, lzip int4, rzip int4, lcommcode varchar(4), rcommcode varchar(4), route_id varchar(20), maximo_type varchar(30), maximo_seq_num int4, asset_code varchar(50), mrc varchar(8), min_range int4,
      max_range int4
    -> FeatureMerger_2 [input 2]
    -> FeatureMerger [input 1]
FeatureMerger_2
    MERGE_TYPE = Attributes Only
    BUILD_INCOMPLETE = No
    REFERATTR = centerline
    REFEEATTR = centerline_id
    PROCESS_DUPS = No
    COMPLETE -> coagis.coa_street_condition (writer POSTGIS_2)
    INCOMPLETE -> coagis.coa_street_condition (writer POSTGIS_2)
coagis.coa_condition_whole_segments_table (reader POSTGRES_1)
    attributes: centerline numeric(38,8), surfacetype varchar(20), noalligatoring int2, lightalligatoring int2, mediumalligatoring int2, severealligatoring int2, cracking int2, rutting int2, oxidation_raveling int2, ridequality int2, patching int2, curbpresence varchar(50), curbtype1 varchar(50), curbtype2 varchar(50), pcs2009 varchar(3), pcr2009 float8, editor varchar(2), editdate timestamp, comments varchar(200), currentpcr float8, pcrclass varchar(15), pid int4, pcs2009pcr float8, pcs2009class text, edit_date timestamp, edit_by varchar(100), pcr2010 float8, pcr2011 float8, pcr2012 float8
    -> FeatureMerger [input 2]
FeatureMerger
    MERGE_TYPE = Attributes Only
    BUILD_INCOMPLETE = No
    REFERATTR = centerline_id
    REFEEATTR = centerline
    PROCESS_DUPS = No
    COMPLETE -> coagis.coa_street_condition (writer POSTGIS_2)
coagis.coa_street_inventory_not_in_bc_streets (reader POSTGIS_1)
    attributes: objectid int4,PRIKEY, centerline numeric(38,8), frommeasure numeric(38,8), tomeasure numeric(38,8), maint_entity varchar(2), furtherinfo varchar(150), full_street_name varchar(32), surfacetype varchar(20), noalligatoring int2, lightalligatoring int2, mediumalligatoring int2, severealligatoring int2, cracking int2, rutting int2, oxidation_raveling int2, ridequality int2, patching int2, curbpresence varchar(50), curbtype1 varchar(50), curbtype2 varchar(50), pcs2009 varchar(3), pcr2009 numeric(38,8), editor varchar(2), editdate timestamp, comments varchar(200), currentpcr numeric(38,8), class varchar(15), pcs2009pcr numeric(38,8), pcs2009class varchar(15), snowremoval int4,
      edit_date timestamp, edit_by varchar(100)
    -> StringReplacer
StringReplacer
    SRC_ATTRS = maint_entity
    NO_MATCH = _FME_NO_OP_
    REPLACE_TEXT = CITY OF ASHEVILLE
    REGEXP = no
    CASE = no
    FIND_TEXT = C
    -> coagis.coa_street_condition (writer POSTGIS_2)
coagis.coa_street_condition (writer POSTGIS_2)
    attributes: objectid int4,PRIKEY, centerline numeric(38,8), maintenance_entity varchar(20), full_street_name varchar(50), surfacetype varchar(20), noalligatoring int2, lightalligatoring int2, mediumalligatoring int2, severealligatoring int2, cracking int2, rutting int2, oxidation_raveling int2, ridequality int2, patching int2, curbpresence varchar(50), curbtype1 varchar(35), curbtype2 varchar(35), pcs2009 varchar(3), pcr2009 numeric(38,8), editor varchar(2), editdate timestamp, comments varchar(200), currentpcr numeric(38,8), pcrclass varchar(15), pcs2009pcr numeric(38,8), pcs2009class text, edit_date timestamp, edit_by varchar(100)
