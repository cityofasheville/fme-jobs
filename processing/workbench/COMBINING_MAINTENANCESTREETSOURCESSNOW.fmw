FME workspace COMBINING_MAINTENANCESTREETSOURCESSNOW.fmw

Parameters:
- SourceDataset_POSTGRES = coa-gis-edit1b   # Connection
- SourceDataset_POSTGIS = coa-gis-edit1b   # Connection
- DestDataset_POSTGIS = coa-gis-edit1b   # Connection

Readers:
- POSTGRES_1: POSTGRES from $(SourceDataset_POSTGRES)
- POSTGIS_1: POSTGIS from $(SourceDataset_POSTGIS)

Writers:
- POSTGIS_2: POSTGIS to $(DestDataset_POSTGIS)

coagis.coa_street_maintenance_events (reader POSTGIS_1)
    attributes: objectid int4,PRIKEY, centerlineid numeric(38,8), frommeasure numeric(38,8), tomeasure numeric(38,8), maintenance_entity varchar(35), segment_length numeric(38,8), furtherinfo varchar(150), pid int4, snowremoval int4, edit_date timestamp, edit_by varchar(100)
    -> FeatureMerger_2 [input 1]
coagis.bc_street (reader POSTGIS_1)
    attributes: objectid int4,PRIKEY, centerline_id numeric(38,8), road_class int4, street_prefix varchar(2), street_name varchar(30), street_type varchar(4), street_postdirection varchar(2), street_dupe varchar(1), full_street_name varchar(32), speed_limit int4, lane_count int4, left_from_address int4, left_to_address int4, right_from_address int4, right_to_address int4, user_id varchar(8), create_date timestamp, change_date timestamp, lesn int2, resn int2, lzip int4, rzip int4, lcommcode varchar(4), rcommcode varchar(4), route_id varchar(20), maximo_type varchar(30), maximo_seq_num int4, asset_code varchar(50), mrc varchar(8), min_range int4,
      max_range int4
    -> FeatureMerger [input 1]
    -> FeatureMerger_2 [input 2]
FeatureMerger_2
    PROCESS_DUPS = No
    REFERATTR = centerlineid
    REFEEATTR = centerline_id
    BUILD_INCOMPLETE = No
    MERGE_TYPE = Attributes Only
    COMPLETE -> StringReplacer_4
StringReplacer_4
    REGEXP = no
    SRC_ATTRS = snowremoval
    NO_MATCH = _FME_NO_OP_
    FIND_TEXT = 98
    REPLACE_TEXT = PRIVATE
    CASE = no
    -> StringReplacer_5
StringReplacer_5
    REGEXP = no
    SRC_ATTRS = snowremoval
    NO_MATCH = _FME_NO_OP_
    FIND_TEXT = 99
    REPLACE_TEXT = NCDOT
    CASE = no
    -> StringReplacer_6
StringReplacer_6
    REGEXP = no
    SRC_ATTRS = snowremoval
    NO_MATCH = _FME_NO_OP_
    FIND_TEXT = 100
    REPLACE_TEXT = UNKNOWN
    CASE = no
    -> StringReplacer_8
StringReplacer_8
    REGEXP = no
    SRC_ATTRS = snowremoval
    NO_MATCH = _FME_NO_OP_
    FIND_TEXT = 1
    REPLACE_TEXT = PRIMARY
    CASE = no
    -> StringReplacer_9
StringReplacer_9
    REGEXP = no
    SRC_ATTRS = snowremoval
    NO_MATCH = _FME_NO_OP_
    FIND_TEXT = 2
    REPLACE_TEXT = SECONDARY
    CASE = no
    -> StringReplacer_10
StringReplacer_10
    REGEXP = no
    SRC_ATTRS = snowremoval
    NO_MATCH = _FME_NO_OP_
    FIND_TEXT = 3
    REPLACE_TEXT = TERTIARY
    CASE = no
    -> coagis.coa_street_maintenance_snow (writer POSTGIS_2)
coagis.coa_maintenance_whole_segments_table (reader POSTGRES_1)
    attributes: centerlineid float8, maintenance_entity varchar(35), furtherinfo varchar(150), pid int4,PRIKEY, snowremoval int4, edit_date timestamp, edit_by varchar(100)
    -> FeatureMerger [input 2]
FeatureMerger
    PROCESS_DUPS = No
    REFERATTR = centerline_id
    REFEEATTR = centerlineid
    BUILD_INCOMPLETE = No
    MERGE_TYPE = Attributes Only
    COMPLETE -> StringReplacer_2
StringReplacer_2
    REGEXP = no
    SRC_ATTRS = snowremoval
    NO_MATCH = _FME_NO_OP_
    FIND_TEXT = 98
    REPLACE_TEXT = PRIVATE
    CASE = no
    -> StringReplacer_3
StringReplacer_3
    REGEXP = no
    SRC_ATTRS = snowremoval
    NO_MATCH = _FME_NO_OP_
    FIND_TEXT = 99
    REPLACE_TEXT = NCDOT
    CASE = no
    -> StringReplacer_7
StringReplacer_7
    REGEXP = no
    SRC_ATTRS = snowremoval
    NO_MATCH = _FME_NO_OP_
    FIND_TEXT = 100
    REPLACE_TEXT = UNKNOWN
    CASE = no
    -> StringReplacer_14
StringReplacer_14
    REGEXP = no
    SRC_ATTRS = snowremoval
    NO_MATCH = _FME_NO_OP_
    FIND_TEXT = 1
    REPLACE_TEXT = PRIMARY
    CASE = no
    -> StringReplacer_15
StringReplacer_15
    REGEXP = no
    SRC_ATTRS = snowremoval
    NO_MATCH = _FME_NO_OP_
    FIND_TEXT = 2
    REPLACE_TEXT = SECONDARY
    CASE = no
    -> StringReplacer_16
StringReplacer_16
    REGEXP = no
    SRC_ATTRS = snowremoval
    NO_MATCH = _FME_NO_OP_
    FIND_TEXT = 3
    REPLACE_TEXT = TERTIARY
    CASE = no
    -> coagis.coa_street_maintenance_snow (writer POSTGIS_2)
coagis.coa_street_inventory_not_in_bc_streets (reader POSTGIS_1)
    attributes: objectid int4,PRIKEY, centerline numeric(38,8), frommeasure numeric(38,8), tomeasure numeric(38,8), maint_entity varchar(2), furtherinfo varchar(150), full_street_name varchar(32), surfacetype varchar(20), noalligatoring int2, lightalligatoring int2, mediumalligatoring int2, severealligatoring int2, cracking int2, rutting int2, oxidation_raveling int2, ridequality int2, patching int2, curbpresence varchar(50), curbtype1 varchar(50), curbtype2 varchar(50), pcs2009 varchar(3), pcr2009 numeric(38,8), editor varchar(2), editdate timestamp, comments varchar(200), currentpcr numeric(38,8), class varchar(15), pcs2009pcr numeric(38,8), pcs2009class varchar(15), snowremoval int4,
      edit_date timestamp, edit_by varchar(100)
    -> StringReplacer
StringReplacer
    REGEXP = no
    SRC_ATTRS = maint_entity
    NO_MATCH = _FME_NO_OP_
    FIND_TEXT = C
    REPLACE_TEXT = CITY OF ASHEVILLE
    CASE = no
    -> StringReplacer_11
StringReplacer_11
    REGEXP = no
    SRC_ATTRS = snowremoval
    NO_MATCH = _FME_NO_OP_
    FIND_TEXT = 1
    REPLACE_TEXT = PRIMARY
    CASE = no
    -> StringReplacer_12
StringReplacer_12
    REGEXP = no
    SRC_ATTRS = snowremoval
    NO_MATCH = _FME_NO_OP_
    FIND_TEXT = 2
    REPLACE_TEXT = SECONDARY
    CASE = no
    -> StringReplacer_13
StringReplacer_13
    REGEXP = no
    SRC_ATTRS = snowremoval
    NO_MATCH = _FME_NO_OP_
    FIND_TEXT = 3
    REPLACE_TEXT = TERTIARY
    CASE = no
    -> coagis.coa_street_maintenance_snow (writer POSTGIS_2)
coagis.coa_street_maintenance_snow (writer POSTGIS_2)
    attributes: objectid int4,PRIKEY, centerline_id varchar(20), full_street_name varchar(50), maintenance_entity varchar(30), furtherinfo varchar(150), frommeasure numeric(38,8), tomeasure numeric(38,8), snowremoval varchar(25), edit_date timestamp, edit_by varchar(100)
