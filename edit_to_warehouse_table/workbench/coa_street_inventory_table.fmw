FME workspace coa_street_inventory_table.fmw

Parameters:
- SourceDataset_POSTGRES = coa-gis-edit1b   # Connection
- DestDataset_POSTGRES = coa-gis-warehouse1-TABLE   # Connection

Readers:
- POSTGRES_1: POSTGRES from $(SourceDataset_POSTGRES)

Writers:
- POSTGRES_2: POSTGRES to $(DestDataset_POSTGRES)

coagis.coa_street_inventory_table (reader POSTGRES_1)
    attributes: uniqueid int4,PRIKEY, lengthdiff float8, pb_year_updated int4, street_name varchar(44), date_accepted timestamp, beginningat varchar(64), endingat varchar(67), length float8, avg_width float8, streetcomments varchar(255), square_feet int4, lengthfeet int4, doc_rw varchar(50), rw varchar(64), rw_platbook varchar(59), rw_updated timestamp, rw_comments varchar(25), old_sr_num varchar(10), rw_researched_by varchar(100), problem_description varchar(100), edit_date timestamp, edit_by varchar(100)
    -> coagis.coa_street_inventory_table (writer POSTGRES_2)
coagis.coa_street_inventory_table (writer POSTGRES_2)
    attributes: uniqueid int4, lengthdiff numeric(38,8), pb_year_updated int4, street_name varchar(44), date_accepted timestamp, beginningat varchar(64), endingat varchar(67), length numeric(38,8), avg_width numeric(38,8), streetcomments varchar(255), square_feet int4, lengthfeet int4, doc_rw varchar(50), rw varchar(64), rw_platbook varchar(59), rw_updated timestamp, rw_comments varchar(25), old_sr_num varchar(10), rw_researched_by varchar(100), problem_description varchar(100), edit_date timestamp, edit_by varchar(100)
