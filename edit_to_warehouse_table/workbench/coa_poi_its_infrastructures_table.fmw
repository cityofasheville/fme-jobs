FME workspace coa_poi_its_infrastructures_table.fmw

Parameters:
- SourceDataset_POSTGRES = coa-gis-edit1b   # Connection
- DestDataset_POSTGRES = coa-gis-warehouse1b   # Connection

Readers:
- POSTGRES_1: POSTGRES from $(SourceDataset_POSTGRES)

Writers:
- POSTGRES_2: POSTGRES to $(DestDataset_POSTGRES)

coagis.coa_poi_its_infrastructures_table (reader POSTGRES_1)
    attributes: pid int4,PRIKEY, pois_pid int8, name varchar(50), narrative varchar(155), owner int8, it_user int8, type int8, subtype int8, speed numeric(18,2), directional varchar(50), sec int8, edit_date timestamp, edit_by varchar(100)
    -> coagis.coa_poi_its_infrastructures_table (writer POSTGRES_2)
coagis.coa_poi_its_infrastructures_table (writer POSTGRES_2)
    attributes: pid int4,PRIKEY, pois_pid numeric(19,0), name varchar(50), narrative varchar(155), owner numeric(19,0), it_user numeric(19,0), type numeric(19,0), subtype numeric(19,0), speed numeric(18,2), directional varchar(50), sec numeric(19,0), edit_date timestamp, edit_by varchar(100)
