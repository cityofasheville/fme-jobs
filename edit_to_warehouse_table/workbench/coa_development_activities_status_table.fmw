FME workspace coa_development_activities_status_table.fmw

Parameters:
- SourceDataset_POSTGRES = coa-gis-edit1b   # Connection
- DestDataset_POSTGRES = coa-gis-warehouse1b   # Connection
- SourceDataset_POSTGRES_3 = coa-gis-edit1b   # Connection
- DestDataset_POSTGRES_3 = coa-gis-warehouse1b   # Connection

Readers:
- POSTGRES_1: POSTGRES from $(SourceDataset_POSTGRES)
- POSTGRES_3: POSTGRES

Writers:
- POSTGRES_2: POSTGRES to $(DestDataset_POSTGRES)
- POSTGRES_4: POSTGRES to $(DestDataset_POSTGRES_3)

coagis.coa_development_activities_status_table (reader POSTGRES_3)
    attributes: objectid int4,PRIKEY, status varchar(100), name varchar(50), edit_date timestamp, edit_by varchar(100)
    -> coagis.coa_development_activities_status_table (writer POSTGRES_4)
coagis.coa_development_activities_status_table (writer POSTGRES_4)
    attributes: objectid int4, status varchar(100), name varchar(50), edit_date timestamp, edit_by varchar(100)
