FME workspace coa_airport_propoerty_table.fmw

Parameters:
- SourceDataset_POSTGRES = coa-gis-edit1b   # Connection
- DestDataset_POSTGRES = coa-gis-warehouse1b   # Connection

Readers:
- POSTGRES_1: POSTGRES from $(SourceDataset_POSTGRES)

Writers:
- POSTGRES_2: POSTGRES to $(DestDataset_POSTGRES)

coagis.coa_airport_property_table (reader POSTGRES_1)
    attributes: control_nbr int4,PRIKEY, pin_nbr varchar(50), department varchar(50), street_nbr varchar(50), location varchar(50), neighborhood varchar(50), county varchar(50), use_function varchar(50), description_land varchar(1000), land_area varchar(50), surveyed_by varchar(50), date_of_survey timestamp, plat_book_page varchar(50), description_improvements varchar(1000), improvements_area varchar(50), fixtures_equipment varchar(1000), safety_or_environmental varchar(1000), zoning varchar(50), floodplain varchar(10), historic_district varchar(10), date_acquired timestamp, grantor varchar(50), intrument_of_conveyance varchar(50), deed_book_page varchar(50), deed_restrictions varchar(1000), title_opinion_by varchar(50), date_of_title_opinion timestamp, liens_encumberances varchar(1000), date_retired timestamp, reason_retired varchar(50),
      grantee varchar(50), comments varchar(1000), oldpin varchar(50), acquisition_cost numeric(38,2), insurance_value numeric(38,2), fair_market_value numeric(38,2), tax_value numeric(38,2), sale_price numeric(38,2), edit_date timestamp, edit_by varchar(100)
    -> coagis.coa_airport_property_table (writer POSTGRES_2)
coagis.coa_airport_property_table (writer POSTGRES_2)
    attributes: control_nbr int4,PRIKEY, pin_nbr varchar(50), department varchar(50), street_nbr varchar(50), location varchar(50), neighborhood varchar(50), county varchar(50), use_function varchar(50), description_land varchar(1000), land_area varchar(50), surveyed_by varchar(50), date_of_survey timestamp, plat_book_page varchar(50), description_improvements varchar(1000), improvements_area varchar(50), fixtures_equipment varchar(1000), safety_or_environmental varchar(1000), zoning varchar(50), floodplain bool, historic_district bool, date_acquired timestamp, grantor varchar(50), intrument_of_conveyance varchar(50), deed_book_page varchar(50), deed_restrictions varchar(1000), title_opinion_by varchar(50), date_of_title_opinion timestamp, liens_encumberances varchar(1000), date_retired timestamp, reason_retired varchar(50),
      grantee varchar(50), comments varchar(1000), oldpin varchar(50), acquisition_cost numeric(38,2), insurance_value numeric(38,2), fair_market_value numeric(38,2), tax_value numeric(38,2), sale_price numeric(38,2), edit_date timestamp, edit_by varchar(100)
