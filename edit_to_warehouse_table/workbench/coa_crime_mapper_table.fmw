FME workspace coa_crime_mapper_table.fmw

Parameters:
- SourceDataset_POSTGRES = coa-gis-edit1b   # Connection
- DestDataset_POSTGRES = coa-gis-warehouse1b   # Connection
- DestDataset_POSTGRES_4 = coa-gis-warehouse1b   # Connection

Readers:
- POSTGRES_1: POSTGRES from $(SourceDataset_POSTGRES)

Writers:
- POSTGRES_2: POSTGRES to $(DestDataset_POSTGRES)
- POSTGRES_3: POSTGRES to $(DestDataset_POSTGRES_4)

coagis.coa_crime_mapper_table (reader POSTGRES_1)
    attributes: source varchar(25), idnum varchar(25), casenumber varchar(25), severity varchar(50), thedate timestamp, ucr int4, offense varchar(50), address varchar(150), x numeric(14,2), y numeric(14,2), crimemapper varchar(10), agency varchar(50), edit_date timestamp, edit_by varchar(100)
    -> coagis.coa_crime_mapper_table (writer POSTGRES_3)
coagis.coa_crime_mapper_table (writer POSTGRES_3)
    attributes: source varchar(25), idnum varchar(25), casenumber varchar(25), severity varchar(25), thedate timestamp, ucr int4, offense varchar(25), address varchar(150), x numeric(14,2), y numeric(14,2), crimemapper varchar(3), agency varchar(50), edit_date timestamp, edit_by varchar(100), pid serial,PRIKEY
