FME workspace coa_adoptastreets_orgs_table.fmw

Parameters:
- SourceDataset_POSTGRES = coa-gis-edit1b   # Connection
- DestDataset_POSTGRES = coa-gis-warehouse1b   # Connection

Readers:
- POSTGRES_1: POSTGRES from $(SourceDataset_POSTGRES)

Writers:
- POSTGRES_2: POSTGRES to $(DestDataset_POSTGRES)

coagis.coa_adoptastreets_orgs_table (reader POSTGRES_1)
    attributes: orgid int4,PRIKEY, orgname varchar(150), orgphonemain varchar(25), orgphonealtone varchar(25), orgphonealttwo varchar(25), orgemailone varchar(150), orgemailtwo varchar(150), orgfax varchar(25), orgfname varchar(150), orglname varchar(150), orgaddress varchar(255), orgcity varchar(50), orgstate varchar(25), orgzip varchar(5), edit_date timestamp, edit_by varchar(100)
    -> coagis.coa_adoptastreets_orgs_table (writer POSTGRES_2)
coagis.coa_adoptastreets_orgs_table (writer POSTGRES_2)
    attributes: orgid int4, orgname varchar(150), orgphonemain varchar(25), orgphonealtone varchar(25), orgphonealttwo varchar(25), orgemailone varchar(150), orgemailtwo varchar(150), orgfax varchar(25), orgfname varchar(150), orglname varchar(150), orgaddress varchar(255), orgcity varchar(50), orgstate varchar(25), orgzip varchar(5), edit_date timestamp, edit_by varchar(100)
