FME workspace coa_adoptastreets_sources_table.fmw

Parameters:
- SourceDataset_POSTGRES = coa-gis-edit1b   # Connection
- DestDataset_POSTGRES = coa-gis-warehouse1b   # Connection

Readers:
- POSTGRES_1: POSTGRES from $(SourceDataset_POSTGRES)

Writers:
- POSTGRES_2: POSTGRES to $(DestDataset_POSTGRES)

coagis.coa_adoptastreets_sources_table (reader POSTGRES_1)
    attributes: sourceid int4,PRIKEY, sourcename varchar(150), edit_date timestamp, edit_by varchar(100), signnarriative varchar(255)
    -> coagis.coa_adoptastreets_sources_table (writer POSTGRES_2)
coagis.coa_adoptastreets_sources_table (writer POSTGRES_2)
    attributes: sourceid int4, sourcename varchar(150), sourcenarriative varchar(255), edit_date timestamp, edit_by varchar(100)
