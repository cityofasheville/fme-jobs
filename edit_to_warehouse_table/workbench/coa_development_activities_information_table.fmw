FME workspace coa_development_activities_information_table.fmw

Parameters:
- SourceDataset_POSTGRES = coa-gis-edit1b   # Connection
- DestDataset_POSTGRES = coa-gis-warehouse1-TABLE   # Connection

Readers:
- POSTGRES_1: POSTGRES from $(SourceDataset_POSTGRES)

Writers:
- POSTGRES_2: POSTGRES to $(DestDataset_POSTGRES)

coagis.coa_development_activities_information_table (reader POSTGRES_1)
    attributes: objectid int4,PRIKEY, name varchar(50), location varchar(200), type int2, project_id varchar(25), edit_date timestamp, edit_by varchar(100)
    -> coagis.coa_development_activities_information_table (writer POSTGRES_2)
coagis.coa_development_activities_information_table (writer POSTGRES_2)
    attributes: objectid int4, name varchar(50), location varchar(200), type int4, project_id varchar(25), edit_date timestamp, edit_by varchar(100)
