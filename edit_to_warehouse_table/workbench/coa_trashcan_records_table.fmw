FME workspace coa_trashcan_records_table.fmw

Parameters:
- SourceDataset_POSTGRES = coa-gis-edit1b   # Connection
- DestDataset_POSTGRES = coa-gis-warehouse1-TABLE   # Connection

Readers:
- POSTGRES_1: POSTGRES from $(SourceDataset_POSTGRES)

Writers:
- POSTGRES_2: POSTGRES to $(DestDataset_POSTGRES)

coagis.coa_trashcan_records_table (reader POSTGRES_1)
    attributes: uniqueid int4,PRIKEY, container_number varchar(20), size int4, civicid numeric(38,8), addr varchar(150), pin varchar(15), zipcode int4, comments varchar(255), researchcomments varchar(50), delivery__date timestamp, annualbilling text, mtwth_addrnumber int4, mtwth_streetname varchar(35), mtwth_comments varchar(50), mtwth_containernumber varchar(50), mtwth_2ndcontainernum varchar(50), mtwth_trucknum varchar(50), mtwth_notes varchar(50), mtwth_deliverydate timestamp, mtwth_day varchar(20), oldpinnum varchar(12), overlaynewpinnum varchar(2), accountnumber int8, edit_date timestamp, edit_by varchar(100), addressvalidated bool
    -> coagis.coa_trashcan_records_table (writer POSTGRES_2)
coagis.coa_trashcan_records_table (writer POSTGRES_2)
    attributes: uniqueid int4,PRIKEY, container_number varchar(20), size int4, civicid numeric(38,8), addr varchar(150), pin varchar(15), zipcode int4, comments varchar(255), researchcomments varchar(50), delivery__date timestamp, annualbilling varchar(254), mtwth_addrnumber int4, mtwth_streetname varchar(35), mtwth_comments varchar(50), mtwth_containernumber varchar(50), mtwth_2ndcontainernum varchar(50), mtwth_trucknum varchar(50), mtwth_notes varchar(50), mtwth_deliverydate timestamp, mtwth_day varchar(20), oldpinnum varchar(12), overlaynewpinnum varchar(2), accountnumber numeric(19,0), edit_date timestamp, edit_by varchar(100), addressvalidated varchar(10)
