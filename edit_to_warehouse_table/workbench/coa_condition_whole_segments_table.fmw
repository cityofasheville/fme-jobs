FME workspace coa_condition_whole_segments_table.fmw

Parameters:
- DestDataset_POSTGRES = coa-gis-warehouse1b   # Connection
- SourceDataset_POSTGRES = coa-gis-edit1b   # Connection
- DestDataset_POSTGRES_4 = coa-gis-warehouse1-TABLE   # Connection

Readers:
- POSTGRES_1: POSTGRES from $(SourceDataset_POSTGRES)

Writers:
- POSTGRES_2: POSTGRES to $(DestDataset_POSTGRES)
- POSTGRES_3: POSTGRES to $(DestDataset_POSTGRES_4)

coagis.coa_condition_whole_segments_table (reader POSTGRES_1)
    attributes: centerline numeric(38,8), surfacetype varchar(20), noalligatoring int2, lightalligatoring int2, mediumalligatoring int2, severealligatoring int2, cracking int2, rutting int2, oxidation_raveling int2, ridequality int2, patching int2, curbpresence varchar(50), curbtype1 varchar(50), curbtype2 varchar(50), pcs2009 varchar(3), pcr2009 float8, editor varchar(2), editdate timestamp, comments varchar(200), currentpcr float8, pcrclass varchar(15), pid int4, pcs2009pcr float8, pcs2009class text, edit_date timestamp, edit_by varchar(100), pcr2010 float8, pcr2011 float8, pcr2012 float8
    -> coagis.coa_condition_whole_segments_table (writer POSTGRES_3)
coagis.coa_condition_whole_segments_table (writer POSTGRES_3)
    attributes: centerline numeric(38,8), surfacetype varchar(20), noalligatoring int4, lightalligatoring int4, mediumalligatoring int4, severealligatoring int4, cracking int4, rutting int4, oxidation_raveling int4, ridequality int4, patching int4, curbpresence varchar(50), curbtype1 varchar(50), curbtype2 varchar(50), pcs2009 varchar(3), pcr2009 numeric(38,8), editor varchar(2), editdate timestamp, comments varchar(200), currentpcr numeric(38,8), pcrclass varchar(15), pid int4, pcs2009pcr numeric(38,8), pcs2009class varchar(1000), edit_date timestamp, edit_by varchar(100)
