FME workspace coa_muniscpfinput.fmw

Parameters:
- SourceDataset_POSTGRES = coa-gis-edit1b   # Connection
- DestDataset_POSTGRES = coa-gis-warehouse1-TABLE   # Connection

Readers:
- POSTGRES_1: POSTGRES from $(SourceDataset_POSTGRES)

Writers:
- POSTGRES_2: POSTGRES to $(DestDataset_POSTGRES)

coagis.coa_muniscpfinput (reader POSTGRES_1)
    attributes: 1 varchar(60), 2 varchar(60), 3 varchar(60), 4 varchar(60), 5 varchar(60), 6 varchar(60), 7 varchar(60), 8 varchar(60), 9 varchar(60), 10 varchar(60), 11 varchar(60), 12 varchar(60), 13 varchar(60), 14 varchar(60), 15 varchar(60), 16 varchar(60), 17 varchar(60), 18 varchar(60), 19 varchar(60), 20 varchar(60), 21 varchar(60), 22 varchar(60), 23 varchar(60), 24 varchar(60), 25 varchar(60), 26 varchar(60), 27 varchar(60), 28 varchar(60), 29 varchar(60), 30 varchar(60),
      31 varchar(60), 32 varchar(60), 33 varchar(60), 34 varchar(60), 35 varchar(60), 36 varchar(60), 37 varchar(60), 38 varchar(60), 39 varchar(60), 40 varchar(60), 41 varchar(60), 42 varchar(60), 43 varchar(60), 44 varchar(60), 45 varchar(60), 46 varchar(60), 47 varchar(60), 48 varchar(60), 49 varchar(60), 50 varchar(60), 51 varchar(60), 52 varchar(60), 53 varchar(60), 54 varchar(60), 55 varchar(60), 56 varchar(60), 57 varchar(60), 58 varchar(60), 59 varchar(60), 60 varchar(60),
      61 varchar(60), 62 varchar(60), 63 varchar(60), 64 varchar(60), 65 varchar(60), 66 varchar(60), 67 varchar(60), 68 varchar(60), 69 varchar(60), 70 varchar(60), 71 varchar(60), 72 varchar(60), 73 varchar(60), 74 varchar(60), 75 varchar(60), 76 varchar(60), 77 varchar(60), 78 varchar(60), 79 varchar(60), 80 varchar(60), 81 varchar(60), 82 varchar(60), 83 varchar(60), 84 varchar(60), 85 varchar(60), 86 varchar(60), 87 varchar(60), 88 varchar(60), 89 varchar(60), 90 varchar(60),
      91 varchar(60), 92 varchar(60), 93 varchar(60), 94 varchar(60), 95 varchar(60), 96 varchar(60), 97 varchar(60), 98 varchar(60), 99 varchar(60), 100 varchar(60), 101 varchar(60), 102 varchar(60), 103 varchar(60), 104 varchar(60), 105 varchar(60), 106 varchar(60), 107 varchar(60), 108 varchar(60), 109 varchar(60), 110 varchar(60), 111 varchar(60), 112 varchar(60), 113 varchar(60), 114 varchar(60), 115 varchar(60), 116 varchar(60), 117 varchar(60), 118 varchar(60), 119 varchar(60), 120 varchar(60),
      121 varchar(60), 122 varchar(60), 123 varchar(60), 124 varchar(60), 125 varchar(60), 126 varchar(60), 127 varchar(60), 128 varchar(60), 129 varchar(60), 130 varchar(60), 131 varchar(60), 132 varchar(60), 133 varchar(60), 134 varchar(60), 135 varchar(60), 136 varchar(60), 137 varchar(60), 138 varchar(60), 139 varchar(60), 140 varchar(60), 141 varchar(60), 142 varchar(60), 143 varchar(60), 144 varchar(60), 145 varchar(60), 146 varchar(60), 147 varchar(60), 148 varchar(60), 149 varchar(60), 150 varchar(60),
      151 varchar(60), 152 varchar(60), 153 varchar(60), 154 varchar(60), 155 varchar(60), 156 varchar(60), 157 varchar(60), 158 varchar(60), 159 varchar(60), 160 varchar(60), 161 varchar(60), 162 varchar(60), 163 varchar(60), 164 varchar(60), 165 varchar(60), 166 varchar(60), 167 varchar(60), 168 varchar(60), 169 varchar(60), 170 varchar(60), 171 varchar(60), 172 varchar(60), 173 varchar(60), 174 varchar(60), 175 varchar(60), 176 varchar(60), 177 varchar(60), 178 varchar(60), 179 varchar(60), 180 varchar(60),
      181 varchar(60), 182 varchar(60), 183 varchar(60), 184 varchar(60), 185 varchar(60), 186 varchar(60), 187 varchar(60), 188 varchar(60), 189 varchar(60), 190 varchar(60), 191 varchar(60), 192 varchar(60), 193 varchar(60), 194 varchar(60), 195 varchar(60), 196 varchar(60), 197 varchar(60), 198 varchar(60), 199 varchar(60), 200 varchar(60), 201 varchar(60), 202 varchar(60), 203 varchar(60), 204 varchar(60), 205 varchar(60), 206 varchar(60), 207 varchar(60), 208 varchar(60), 209 varchar(60), 210 varchar(60),
      211 varchar(60), 212 varchar(60), 213 varchar(60), 214 varchar(60), 215 varchar(60), 216 varchar(60), 217 varchar(60), 218 varchar(60), 219 varchar(60), 220 varchar(60), 221 varchar(60)
    -> coagis.coa_muniscpfinput (writer POSTGRES_2)
coagis.coa_muniscpfinput (writer POSTGRES_2)
    attributes: 1 varchar(60), 2 varchar(60), 3 varchar(60), 4 varchar(60), 5 varchar(60), 6 varchar(60), 7 varchar(60), 8 varchar(60), 9 varchar(60), 10 varchar(60), 11 varchar(60), 12 varchar(60), 13 varchar(60), 14 varchar(60), 15 varchar(60), 16 varchar(60), 17 varchar(60), 18 varchar(60), 19 varchar(60), 20 varchar(60), 21 varchar(60), 22 varchar(60), 23 varchar(60), 24 varchar(60), 25 varchar(60), 26 varchar(60), 27 varchar(60), 28 varchar(60), 29 varchar(60), 30 varchar(60),
      31 varchar(60), 32 varchar(60), 33 varchar(60), 34 varchar(60), 35 varchar(60), 36 varchar(60), 37 varchar(60), 38 varchar(60), 39 varchar(60), 40 varchar(60), 41 varchar(60), 42 varchar(60), 43 varchar(60), 44 varchar(60), 45 varchar(60), 46 varchar(60), 47 varchar(60), 48 varchar(60), 49 varchar(60), 50 varchar(60), 51 varchar(60), 52 varchar(60), 53 varchar(60), 54 varchar(60), 55 varchar(60), 56 varchar(60), 57 varchar(60), 58 varchar(60), 59 varchar(60), 60 varchar(60),
      61 varchar(60), 62 varchar(60), 63 varchar(60), 64 varchar(60), 65 varchar(60), 66 varchar(60), 67 varchar(60), 68 varchar(60), 69 varchar(60), 70 varchar(60), 71 varchar(60), 72 varchar(60), 73 varchar(60), 74 varchar(60), 75 varchar(60), 76 varchar(60), 77 varchar(60), 78 varchar(60), 79 varchar(60), 80 varchar(60), 81 varchar(60), 82 varchar(60), 83 varchar(60), 84 varchar(60), 85 varchar(60), 86 varchar(60), 87 varchar(60), 88 varchar(60), 89 varchar(60), 90 varchar(60),
      91 varchar(60), 92 varchar(60), 93 varchar(60), 94 varchar(60), 95 varchar(60), 96 varchar(60), 97 varchar(60), 98 varchar(60), 99 varchar(60), 100 varchar(60), 101 varchar(60), 102 varchar(60), 103 varchar(60), 104 varchar(60), 105 varchar(60), 106 varchar(60), 107 varchar(60), 108 varchar(60), 109 varchar(60), 110 varchar(60), 111 varchar(60), 112 varchar(60), 113 varchar(60), 114 varchar(60), 115 varchar(60), 116 varchar(60), 117 varchar(60), 118 varchar(60), 119 varchar(60), 120 varchar(60),
      121 varchar(60), 122 varchar(60), 123 varchar(60), 124 varchar(60), 125 varchar(60), 126 varchar(60), 127 varchar(60), 128 varchar(60), 129 varchar(60), 130 varchar(60), 131 varchar(60), 132 varchar(60), 133 varchar(60), 134 varchar(60), 135 varchar(60), 136 varchar(60), 137 varchar(60), 138 varchar(60), 139 varchar(60), 140 varchar(60), 141 varchar(60), 142 varchar(60), 143 varchar(60), 144 varchar(60), 145 varchar(60), 146 varchar(60), 147 varchar(60), 148 varchar(60), 149 varchar(60), 150 varchar(60),
      151 varchar(60), 152 varchar(60), 153 varchar(60), 154 varchar(60), 155 varchar(60), 156 varchar(60), 157 varchar(60), 158 varchar(60), 159 varchar(60), 160 varchar(60), 161 varchar(60), 162 varchar(60), 163 varchar(60), 164 varchar(60), 165 varchar(60), 166 varchar(60), 167 varchar(60), 168 varchar(60), 169 varchar(60), 170 varchar(60), 171 varchar(60), 172 varchar(60), 173 varchar(60), 174 varchar(60), 175 varchar(60), 176 varchar(60), 177 varchar(60), 178 varchar(60), 179 varchar(60), 180 varchar(60),
      181 varchar(60), 182 varchar(60), 183 varchar(60), 184 varchar(60), 185 varchar(60), 186 varchar(60), 187 varchar(60), 188 varchar(60), 189 varchar(60), 190 varchar(60), 191 varchar(60), 192 varchar(60), 193 varchar(60), 194 varchar(60), 195 varchar(60), 196 varchar(60), 197 varchar(60), 198 varchar(60), 199 varchar(60), 200 varchar(60), 201 varchar(60), 202 varchar(60), 203 varchar(60), 204 varchar(60), 205 varchar(60), 206 varchar(60), 207 varchar(60), 208 varchar(60), 209 varchar(60), 210 varchar(60),
      211 varchar(60), 212 varchar(60), 213 varchar(60), 214 varchar(60), 215 varchar(60), 216 varchar(60), 217 varchar(60), 218 varchar(60), 219 varchar(60), 220 varchar(60), 221 varchar(60), pid serial,PRIKEY
