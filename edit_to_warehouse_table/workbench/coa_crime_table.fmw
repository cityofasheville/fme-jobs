FME workspace coa_crime_table.fmw

Parameters:
- SourceDataset_POSTGRES = coa-gis-edit1b   # Connection
- DestDataset_POSTGRES = coa-gis-warehouse1-TABLE   # Connection

Readers:
- POSTGRES_1: POSTGRES from $(SourceDataset_POSTGRES)

Writers:
- POSTGRES_2: POSTGRES to $(DestDataset_POSTGRES)

coagis.coa_crime_table (reader POSTGRES_1)
    attributes: source varchar(25), idnum varchar(25), casenumber varchar(25), severity varchar(50), thedate timestamp, ucr int4, chargedescription varchar(100), ucrcode varchar(25), offense varchar(50), address varchar(150), x numeric(14,2), y numeric(14,2), crimemapper varchar(10), arresteename varchar(150), arresteedob timestamp, age varchar(5), sex varchar(50), agency varchar(50), edit_date timestamp, edit_by varchar(100)
    -> coagis.coa_crime_table (writer POSTGRES_2)
coagis.coa_crime_table (writer POSTGRES_2)
    attributes: source varchar(25), idnum varchar(25), casenumber varchar(25), severity varchar(50), thedate timestamp, ucr int4, chargedescription varchar(100), ucrcode varchar(25), offense varchar(50), address varchar(150), x numeric(14,2), y numeric(14,2), crimemapper varchar(10), arresteename varchar(150), arresteedob timestamp, age varchar(5), sex varchar(50), agency varchar(50), edit_date timestamp, edit_by varchar(100), pid serial,PRIKEY
