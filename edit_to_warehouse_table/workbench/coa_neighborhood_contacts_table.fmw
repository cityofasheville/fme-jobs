FME workspace coa_neighborhood_contacts_table.fmw

Parameters:
- SourceDataset_POSTGRES = coa-gis-edit1b   # Connection
- DestDataset_POSTGRES = coa-gis-warehouse1b   # Connection

Readers:
- POSTGRES_1: POSTGRES from $(SourceDataset_POSTGRES)

Writers:
- POSTGRES_2: POSTGRES to $(DestDataset_POSTGRES)

coagis.coa_neighborhood_contacts_table (reader POSTGRES_1)
    attributes: contactid int4,PRIKEY, edit_date timestamp, edit_name varchar(25), nameoforganization varchar(100), firstname varchar(25), lastname varchar(25), address varchar(50), city varchar(25), zip int4, phonenumber varchar(15), altnumber varchar(15), emailaddress varchar(50), comments varchar(255), nbhd_id varchar(10), preferredcontactinfo varchar(255), website varchar(150), contactgroup varchar(150), regularmeetingdate varchar(100), edit_date2 timestamp, edit_by varchar(100)
    -> coagis.coa_neighborhood_contacts_table (writer POSTGRES_2)
coagis.coa_neighborhood_contacts_table (writer POSTGRES_2)
    attributes: contactid int4, edit_date timestamp, edit_name varchar(25), nameoforganization varchar(100), firstname varchar(25), lastname varchar(25), address varchar(50), city varchar(25), zip int4, phonenumber varchar(15), altnumber varchar(15), emailaddress varchar(50), comments varchar(255), nbhd_id varchar(10), preferredcontactinfo varchar(255), website varchar(150), contactgroup varchar(150), regularmeetingdate varchar(100)
