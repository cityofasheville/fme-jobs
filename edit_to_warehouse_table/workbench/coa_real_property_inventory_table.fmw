FME workspace coa_real_property_inventory_table.fmw

Parameters:
- SourceDataset_POSTGRES = coa-gis-edit1b   # Connection
- DestDataset_POSTGRES = coa-gis-warehouse1-TABLE   # Connection

Readers:
- POSTGRES_1: POSTGRES from $(SourceDataset_POSTGRES)

Writers:
- POSTGRES_2: POSTGRES to $(DestDataset_POSTGRES)

coagis.coa_real_property_inventory_table (reader POSTGRES_1)
    attributes: control_nbr int4, pin_nbr varchar(15), status varchar(50), community_development bool, project varchar(50), consider_for_telecom bool, amsl int4, street_nbr varchar(50), location varchar(50), neighborhood varchar(50), department varchar(50), use_function varchar(50), acquisition_cost float4, fair_market_value float4, tax_value float4, insurance_value float4, description_land varchar(500), land_area float8, surveyed_by varchar(50), date_of_survey timestamp, plat_book_page varchar(50), description_improvements varchar(1000), improvements_area int4, fixtures_equipment varchar(1000), zoning varchar(50), floodplain bool, historic_district bool, safety_or_environmental varchar(1000), date_acquired timestamp, grantor varchar(50),
      intrument_of_conveyance varchar(50), deed_book_page varchar(50), title_opinion_by varchar(50), date_of_title_opinion timestamp, deed_restrictions varchar(1000), liens_encumberances varchar(1000), date_retired timestamp, reason_retired varchar(50), sale_price float4, grantee varchar(50), comments varchar(1000), oldpin varchar(15), economic_development bool, edit_date timestamp, edit_by varchar(100)
    -> coagis.coa_real_property_inventory_table (writer POSTGRES_2)
coagis.coa_real_property_inventory_table (writer POSTGRES_2)
    attributes: control_nbr int4, pin_nbr varchar(15), status varchar(50), community_development varchar(10), project varchar(50), consider_for_telecom varchar(10), amsl int4, street_nbr varchar(50), location varchar(50), neighborhood varchar(50), department varchar(50), use_function varchar(50), acquisition_cost numeric(19,4), fair_market_value numeric(19,4), tax_value numeric(19,4), insurance_value numeric(19,4), description_land varchar(500), land_area numeric(38,8), surveyed_by varchar(50), date_of_survey timestamp, plat_book_page varchar(50), description_improvements varchar(1000), improvements_area int4, fixtures_equipment varchar(1000), zoning varchar(50), floodplain varchar(10), historic_district varchar(10), safety_or_environmental varchar(1000), date_acquired timestamp, grantor varchar(50),
      intrument_of_conveyance varchar(50), deed_book_page varchar(50), title_opinion_by varchar(50), date_of_title_opinion timestamp, deed_restrictions varchar(1000), liens_encumberances varchar(1000), date_retired timestamp, reason_retired varchar(50), sale_price numeric(19,4), grantee varchar(50), comments varchar(1000), oldpin varchar(15), edit_date timestamp, edit_by varchar(100), economic_development varchar(10)
