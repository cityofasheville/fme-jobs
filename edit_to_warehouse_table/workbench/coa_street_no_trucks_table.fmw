FME workspace coa_street_no_trucks_table.fmw

Parameters:
- SourceDataset_POSTGRES = coa-gis-edit1b   # Connection
- DestDataset_POSTGRES = coa-gis-warehouse1-TABLE   # Connection

Readers:
- POSTGRES_1: POSTGRES from $(SourceDataset_POSTGRES)

Writers:
- POSTGRES_2: POSTGRES to $(DestDataset_POSTGRES)

coagis.coa_street_no_trucks_table (reader POSTGRES_1)
    attributes: centerline numeric(20,5), notrucks varchar(2), pid int4,PRIKEY, edit_date timestamp, edit_by varchar(100)
    -> coagis.coa_street_no_trucks_table (writer POSTGRES_2)
coagis.coa_street_no_trucks_table (writer POSTGRES_2)
    attributes: centerline numeric(20,5), notrucks varchar(2), pid int4, edit_date timestamp, edit_by varchar(100)
