FME workspace UPDATE_water_Data_to_maxmio_dev.fmw

Parameters:
- DestDataset_GEODATABASE_SDE = maximosde_dev   # Destination ESRI Geodatabase (ArcSDE) Dataset
- SourceDataset_GEODATABASE_SDE = maximosde_dev   # Source ESRI Geodatabase (ArcSDE) Dataset
- GEODATABASE_SDE_IN_PASSWORD_GEODATABASE_SDE =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   # Password
- GEODATABASE_SDE_OUT_PASSWORD_GEODATABASE_SDE =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   # Password

Readers:
- GEODATABASE_SDE_1: GEODATABASE_SDE from $(SourceDataset_GEODATABASE_SDE)

Writers:
- GEODATABASE_SDE_2: GEODATABASE_SDE to $(DestDataset_GEODATABASE_SDE)

MAXIMOGIS.TEMP_CONTROL_VALVE (reader GEODATABASE_SDE_1)
    attributes: geodb_oid integer, OBJECTID integer, FACILITYID char(20), INSTALLDATE date, LOCATIONDESCRIPTION char(200), LIFECYCLESTATUS char(150), SUBTYPE char(150), WORKORDERID char(20), ELEVATION double, OPERATIONALAREA char(150), SOURCE char(150), DIAMETER char(150), MXASSETNUM char(20), MRC char(8), EDIT_DATE date, EDIT_BY char(100), mxsiteid char(8)
    -> MAXIMOGIS.WATER_CONTROL_VALVE (writer GEODATABASE_SDE_2)
MAXIMOGIS.WATER_CONTROL_VALVE (writer GEODATABASE_SDE_2)
    attributes: geodb_oid integer, OBJECTID integer, FACILITYID char(20), INSTALLDATE date, LOCATIONDESCRIPTION char(200), LIFECYCLESTATUS char(150), SUBTYPE char(150), WORKORDERID char(20), ELEVATION double, OPERATIONALAREA char(150), SOURCE char(150), DIAMETER char(150), MRC char(8), EDIT_DATE date, EDIT_BY char(100), MXSITEID char(8), MXASSETNUM char(20), MXCREATIONSTATE smallint, ROWSTAMP integer, MXASSETUID integer
MAXIMOGIS.TEMP_HYDRANT (reader GEODATABASE_SDE_1)
    attributes: geodb_oid integer, OBJECTID integer, FACILITYID char(20), INSTALLDATE date, LIFECYCLESTATUS char(150), WORKORDERID char(20), ELEVATION double, SOURCE char(150), OLDWATERDEPARTMENT integer, OPERATIONALAREA char(150), LOCATIONDESCRIPTION char(50), MAINDIAMETER char(150), MXASSETNUM char(20), MRC char(8), AGENCY char(150), EDIT_DATE date, EDIT_BY char(100), mxsiteid char(8), hydrant_type char(50)
    -> MAXIMOGIS.WATER_HYDRANT (writer GEODATABASE_SDE_2)
MAXIMOGIS.WATER_HYDRANT (writer GEODATABASE_SDE_2)
    attributes: geodb_oid integer, OBJECTID integer, FACILITYID char(20), INSTALLDATE date, LIFECYCLESTATUS char(150), WORKORDERID char(20), ELEVATION double, SOURCE char(150), OLDWATERDEPARTMENT integer, OPERATIONALAREA char(150), LOCATIONDESCRIPTION char(50), MAINDIAMETER char(150), MRC char(8), AGENCY char(150), EDIT_DATE date, EDIT_BY char(100), MXASSETNUM char(20), MXCREATIONSTATE smallint, MXSITEID char(8), ROWSTAMP integer, hydrant_type char(50)
MAXIMOGIS.TEMP_LATERAL_LINE (reader GEODATABASE_SDE_1)
    attributes: geodb_oid integer, OBJECTID integer, FACILITYID char(20), INSTALLDATE date, LIFECYCLESTATUS char(150), SUBTYPE char(150), WORKORDERID char(20), RENEWALDATE date, LOCATIONDESCRIPTION char(50), MATERIAL char(150), DIAMETER char(150), MXASSETNUM char(20), MRC char(8), EDIT_DATE date, EDIT_BY char(100), mxsiteid char(8), SHAPE.STLength() double
    -> MAXIMOGIS.WATER_LATERAL_LINE (writer GEODATABASE_SDE_2)
MAXIMOGIS.WATER_LATERAL_LINE (writer GEODATABASE_SDE_2)
    attributes: geodb_oid integer, OBJECTID integer, FACILITYID char(20), INSTALLDATE date, LIFECYCLESTATUS char(150), SUBTYPE char(150), WORKORDERID char(20), RENEWALDATE date, LOCATIONDESCRIPTION char(50), MATERIAL char(150), DIAMETER char(150), MRC char(8), EDIT_DATE date, EDIT_BY char(100), MXSITEID char(8), MXASSETNUM char(20), MXCREATIONSTATE smallint, ROWSTAMP integer, MXASSETUID integer, SHAPE_STLength__ double
MAXIMOGIS.TEMP_SAMPLE_SITES (reader GEODATABASE_SDE_1)
    attributes: geodb_oid integer, OBJECTID integer, FIELD1 integer, UNIQUE_CODE char(5), SITE_NAME char(50), ADDRESS char(50), CITY char(25), JANUARY char(10), FEBRUARY char(10), MARCH char(10), APRIL char(10), MAY char(10), JUNE char(10), JULY char(10), AUGUST char(10), SEPTEMBER char(10), OCTOBER char(10), NOVEMBER char(10), DECEMBER char(10), ZONE char(30), MXASSETNUM char(20), MRC char(8), WRNTY_START date, WRNTY_END date, EDIT_DATE date, EDIT_BY char(100), mxsiteid char(8)
    -> MAXIMOGIS.WATER_SAMPLE_SITES (writer GEODATABASE_SDE_2)
MAXIMOGIS.WATER_SAMPLE_SITES (writer GEODATABASE_SDE_2)
    attributes: geodb_oid integer, OBJECTID integer, FIELD1 integer, UNIQUE_CODE char(5), SITE_NAME char(50), ADDRESS char(50), CITY char(25), JANUARY char(10), FEBRUARY char(10), MARCH char(10), APRIL char(10), MAY char(10), JUNE char(10), JULY char(10), AUGUST char(10), SEPTEMBER char(10), OCTOBER char(10), NOVEMBER char(10), DECEMBER char(10), ZONE char(30), MRC char(8), WRNTY_START date, WRNTY_END date, EDIT_DATE date, EDIT_BY char(100), MXSITEID char(8), MXASSETNUM char(20), MXCREATIONSTATE smallint, ROWSTAMP integer, MXASSETUID integer
MAXIMOGIS.TEMP_SYSTEM_VALVE (reader GEODATABASE_SDE_1)
    attributes: geodb_oid integer, OBJECTID integer, FACILITYID char(20), INSTALLDATE date, WORKORDERID char(20), ELEVATION double, BYPASSVALVE char(150), DIRECTIONTOCLOSE char(150), CURRENTLYOPEN char(150), MOTORIZED char(150), NORMALLYOPEN char(150), TURNSTOCLOSE smallint, VALVESIZE char(150), LOCATIONDESCRIPTION char(50), OPERATIONALAREA char(150), LIFECYCLESTATUS char(150), SOURCE char(150), OLDWATERDEPARTMENT integer, VALVETYPE char(150), SUBTYPE char(150), MXASSETNUM char(20), MRC char(8), EDIT_DATE date, EDIT_BY char(100), mxsiteid char(8), mxcreationstate smallint, mxassetuid integer
    -> MAXIMOGIS.WATER_SYSTEM_VALVE (writer GEODATABASE_SDE_2)
MAXIMOGIS.WATER_SYSTEM_VALVE (writer GEODATABASE_SDE_2)
    attributes: geodb_oid integer, OBJECTID integer, FACILITYID char(20), INSTALLDATE date, WORKORDERID char(20), ELEVATION double, BYPASSVALVE char(150), DIRECTIONTOCLOSE char(150), CURRENTLYOPEN char(150), MOTORIZED char(150), NORMALLYOPEN char(150), TURNSTOCLOSE smallint, VALVESIZE char(150), LOCATIONDESCRIPTION char(50), OPERATIONALAREA char(150), LIFECYCLESTATUS char(150), SOURCE char(150), OLDWATERDEPARTMENT integer, VALVETYPE char(150), SUBTYPE char(150), MRC char(8), EDIT_DATE date, EDIT_BY char(100), MXSITEID char(8), MXASSETNUM char(20), MXCREATIONSTATE smallint, ROWSTAMP integer, MXASSETUID integer
MAXIMOGIS.TEMP_WATER_FLUSHING_POINTS (reader GEODATABASE_SDE_1)
    attributes: geodb_oid integer, OBJECTID integer, ADDRESS char(150), SETTING char(150), TYPE char(150), PLANT char(50), LAST_MOD_DATE date, LAST_MOD_BY char(32), MAXIMO_TYPE char(30), MAXIMO_SEQ_NUM integer, ASSET_CODE char(50), MRC char(8), EDIT_DATE date, EDIT_BY char(100), MXASSETNUM char(20), mxsiteid char(8)
    -> MAXIMOGIS.WATER_FLUSHING_POINTS (writer GEODATABASE_SDE_2)
MAXIMOGIS.WATER_FLUSHING_POINTS (writer GEODATABASE_SDE_2)
    attributes: geodb_oid integer, OBJECTID integer, ADDRESS char(150), SETTING char(150), TYPE char(150), PLANT char(50), LAST_MOD_DATE date, LAST_MOD_BY char(32), MAXIMO_TYPE char(30), MAXIMO_SEQ_NUM integer, ASSET_CODE char(50), MRC char(8), EDIT_DATE date, EDIT_BY char(100), MXASSETNUM char(20), mxsiteid char(8), ROWSTAMP integer, MXASSETUID integer
MAXIMOGIS.TEMP_UNDERGROUND_ENCLOSURE (reader GEODATABASE_SDE_1)
    attributes: geodb_oid integer, OBJECTID integer, FACILITYID char(20), INSTALLDATE date, SUBTYPE char(100), WORKORDERID char(20), ELEVATION double, COVERMATERIAL char(150), COVERTYPE char(20), DEPTH double, INVERTELEVATION double, OPERATIONALAREA char(150), LIFECYCLESTATUS char(150), LOCATIONDESCRIPTION char(75), MXASSETNUM char(20), MRC char(8), EDIT_DATE date, EDIT_BY char(100), mxsiteid char(8), SHAPE.STArea() double, SHAPE.STLength() double
    -> MAXIMOGIS.WATER_UNDERGROUND_ENCLOSURE (writer GEODATABASE_SDE_2)
MAXIMOGIS.WATER_UNDERGROUND_ENCLOSURE (writer GEODATABASE_SDE_2)
    attributes: geodb_oid integer, OBJECTID integer, FACILITYID char(20), INSTALLDATE date, SUBTYPE char(100), WORKORDERID char(20), ELEVATION double, COVERMATERIAL char(150), COVERTYPE char(20), DEPTH double, INVERTELEVATION double, OPERATIONALAREA char(150), LIFECYCLESTATUS char(150), LOCATIONDESCRIPTION char(75), MRC char(8), EDIT_DATE date, EDIT_BY char(100), MXSITEID char(8), MXASSETNUM char(20), MXCREATIONSTATE smallint, ROWSTAMP integer, MXASSETUID integer, SHAPE_STArea__ double, SHAPE_STLength__ double
MAXIMOGIS.TEMP_GRAVITY_MAIN (reader GEODATABASE_SDE_1)
    attributes: geodb_oid integer, OBJECTID integer, FACILITYID char(20), INSTALLDATE date, LIFECYCLESTATUS char(150), WORKORDERID char(20), SLOPE double, MATERIAL char(150), SOURCE char(150), OPERATIONALAREA char(150), DIAMETER char(150), MXASSETNUM char(20), MRC char(8), WRNTY_START date, WRNTY_END date, EDIT_DATE date, EDIT_BY char(100), DIAMETERINT double, mxsiteid char(8), SHAPE.STLength() double
    -> MAXIMOGIS.WATER_GRAVITY_MAIN (writer GEODATABASE_SDE_2)
MAXIMOGIS.WATER_GRAVITY_MAIN (writer GEODATABASE_SDE_2)
    attributes: geodb_oid integer, OBJECTID integer, FACILITYID char(20), INSTALLDATE date, LIFECYCLESTATUS char(150), WORKORDERID char(20), SLOPE double, MATERIAL char(150), SOURCE char(150), OPERATIONALAREA char(150), DIAMETER char(150), MRC char(8), WRNTY_START date, WRNTY_END date, EDIT_DATE date, EDIT_BY char(100), DIAMETERINT double, MXSITEID char(8), MXASSETNUM char(20), MXCREATIONSTATE smallint, ROWSTAMP integer, MXASSETUID integer, SHAPE_STLength__ double
