FME workspace MAXIMOSDE_add_data_dev.fmw

Parameters:
- SourceDataset_GEODATABASE_SDE = maximosde_dev   # Source ESRI Geodatabase (ArcSDE) Dataset
- DestDataset_GEODATABASE_SDE = maximosde_dev   # Destination ESRI Geodatabase (ArcSDE) Dataset
- GEODATABASE_SDE_IN_PASSWORD_GEODATABASE_SDE =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   # Password
- GEODATABASE_SDE_OUT_PASSWORD_GEODATABASE_SDE =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   # Password

Readers:
- GEODATABASE_SDE_1: GEODATABASE_SDE from $(SourceDataset_GEODATABASE_SDE)

Writers:
- GEODATABASE_SDE_2: GEODATABASE_SDE to $(DestDataset_GEODATABASE_SDE)

MAXIMOGIS.WATER_BC_STREET (reader GEODATABASE_SDE_1)
    attributes: geodb_oid integer, OBJECTID integer, CENTERLINE_ID double, ROAD_CLASS integer, STREET_PREFIX char(2), STREET_NAME char(30), STREET_TYPE char(4), STREET_POSTDIRECTION char(2), STREET_DUPE char(1), FULL_STREET_NAME char(32), SPEED_LIMIT integer, LANE_COUNT integer, LEFT_FROM_ADDRESS integer, LEFT_TO_ADDRESS integer, RIGHT_FROM_ADDRESS integer, RIGHT_TO_ADDRESS integer, USER_ID char(8), CREATE_DATE date, CHANGE_DATE date, LESN smallint, RESN smallint, LZIP integer, RZIP integer, LCOMMCODE char(4), RCOMMCODE char(4), ROUTE_ID char(20), MXASSETNUM char(20), MRC char(8), MIN_RANGE integer, MAX_RANGE integer,
      mxsiteid char(8), SHAPE.STLength() double
    -> ChangeDetector_2 [input 1]
MAXIMOGIS.WATER_CONTROL_VALVE (reader GEODATABASE_SDE_1)
    attributes: geodb_oid integer, OBJECTID integer, FACILITYID char(20), INSTALLDATE date, LOCATIONDESCRIPTION char(200), LIFECYCLESTATUS char(150), SUBTYPE char(150), WORKORDERID char(20), ELEVATION double, OPERATIONALAREA char(150), SOURCE char(150), DIAMETER char(150), MRC char(8), EDIT_DATE date, EDIT_BY char(100), MXSITEID char(8), MXASSETNUM char(20), MXCREATIONSTATE smallint, ROWSTAMP integer, MXASSETUID integer
    -> ChangeDetector_3 [input 1]
MAXIMOGIS.WATER_SYSTEM_VALVE (reader GEODATABASE_SDE_1)
    attributes: geodb_oid integer, OBJECTID integer, FACILITYID char(20), INSTALLDATE date, WORKORDERID char(20), ELEVATION double, BYPASSVALVE char(150), DIRECTIONTOCLOSE char(150), CURRENTLYOPEN char(150), MOTORIZED char(150), NORMALLYOPEN char(150), TURNSTOCLOSE smallint, VALVESIZE char(150), LOCATIONDESCRIPTION char(50), OPERATIONALAREA char(150), LIFECYCLESTATUS char(150), SOURCE char(150), OLDWATERDEPARTMENT integer, VALVETYPE char(150), SUBTYPE char(150), MRC char(8), EDIT_DATE date, EDIT_BY char(100), MXSITEID char(8), MXASSETNUM char(20), MXCREATIONSTATE smallint, ROWSTAMP integer, MXASSETUID integer
    -> ChangeDetector_7 [input 1]
MAXIMOGIS.TEMP_BC_STREET (reader GEODATABASE_SDE_1)
    attributes: geodb_oid integer, OBJECTID integer, CENTERLINE_ID double, ROAD_CLASS integer, STREET_PREFIX char(2), STREET_NAME char(30), STREET_TYPE char(4), STREET_POSTDIRECTION char(2), STREET_DUPE char(1), FULL_STREET_NAME char(32), SPEED_LIMIT integer, LANE_COUNT integer, LEFT_FROM_ADDRESS integer, LEFT_TO_ADDRESS integer, RIGHT_FROM_ADDRESS integer, RIGHT_TO_ADDRESS integer, USER_ID char(8), CREATE_DATE date, CHANGE_DATE date, LESN smallint, RESN smallint, LZIP integer, RZIP integer, LCOMMCODE char(4), RCOMMCODE char(4), ROUTE_ID char(20), MXASSETNUM char(20), MRC char(8), MIN_RANGE integer, MAX_RANGE integer,
      mxsiteid char(8), SHAPE.STLength() double
    -> ChangeDetector_2 [input 2]
ChangeDetector_2
    BLANK_AND_MISSING_DIFFER = No
    MATCH = NONE
    MATCHATTRS = MXASSETNUM
    MATCH_ALL = No
    LENIENT_MATCH = no
    ADDED -> MAXIMOGIS.WATER_BC_STREET (writer GEODATABASE_SDE_2)
MAXIMOGIS.WATER_BC_STREET (writer GEODATABASE_SDE_2)
    attributes: geodb_oid integer, OBJECTID integer, CENTERLINE_ID double, ROAD_CLASS integer, STREET_PREFIX char(2), STREET_NAME char(30), STREET_TYPE char(4), STREET_POSTDIRECTION char(2), STREET_DUPE char(1), FULL_STREET_NAME char(32), SPEED_LIMIT integer, LANE_COUNT integer, LEFT_FROM_ADDRESS integer, LEFT_TO_ADDRESS integer, RIGHT_FROM_ADDRESS integer, RIGHT_TO_ADDRESS integer, USER_ID char(8), CREATE_DATE date, CHANGE_DATE date, LESN smallint, RESN smallint, LZIP integer, RZIP integer, LCOMMCODE char(4), RCOMMCODE char(4), ROUTE_ID char(20), MXASSETNUM char(20), MRC char(8), MIN_RANGE integer, MAX_RANGE integer,
      mxsiteid char(8), SHAPE_STLength__ double
MAXIMOGIS.TEMP_CONTROL_VALVE (reader GEODATABASE_SDE_1)
    attributes: geodb_oid integer, OBJECTID integer, FACILITYID char(20), INSTALLDATE date, LOCATIONDESCRIPTION char(200), LIFECYCLESTATUS char(150), SUBTYPE char(150), WORKORDERID char(20), ELEVATION double, OPERATIONALAREA char(150), SOURCE char(150), DIAMETER char(150), MXASSETNUM char(20), MRC char(8), EDIT_DATE date, EDIT_BY char(100), mxsiteid char(8)
    -> ChangeDetector_3 [input 2]
ChangeDetector_3
    BLANK_AND_MISSING_DIFFER = No
    MATCH = NONE
    MATCHATTRS = MXASSETNUM
    MATCH_ALL = No
    LENIENT_MATCH = no
    ADDED -> AttributeCreator_2
AttributeCreator_2
    ATTR_LIST = mxcreationstate,1
    -> MAXIMOGIS.WATER_CONTROL_VALVE (writer GEODATABASE_SDE_2)
MAXIMOGIS.WATER_CONTROL_VALVE (writer GEODATABASE_SDE_2)
    attributes: geodb_oid integer, OBJECTID integer, FACILITYID char(20), INSTALLDATE date, LOCATIONDESCRIPTION char(200), LIFECYCLESTATUS char(150), SUBTYPE char(150), WORKORDERID char(20), ELEVATION double, OPERATIONALAREA char(150), SOURCE char(150), DIAMETER char(150), MRC char(8), EDIT_DATE date, EDIT_BY char(100), MXSITEID char(8), MXASSETNUM char(20), MXCREATIONSTATE smallint, ROWSTAMP integer, MXASSETUID integer
MAXIMOGIS.WATER_GRAVITY_MAIN (reader GEODATABASE_SDE_1)
    attributes: geodb_oid integer, OBJECTID integer, FACILITYID char(20), INSTALLDATE date, LIFECYCLESTATUS char(150), WORKORDERID char(20), SLOPE double, MATERIAL char(150), SOURCE char(150), OPERATIONALAREA char(150), DIAMETER char(150), MRC char(8), WRNTY_START date, WRNTY_END date, EDIT_DATE date, EDIT_BY char(100), DIAMETERINT double, MXSITEID char(8), MXASSETNUM char(20), MXCREATIONSTATE smallint, ROWSTAMP integer, MXASSETUID integer, SHAPE.STLength() double
    -> ChangeDetector_4 [input 1]
MAXIMOGIS.TEMP_GRAVITY_MAIN (reader GEODATABASE_SDE_1)
    attributes: geodb_oid integer, OBJECTID integer, FACILITYID char(20), INSTALLDATE date, LIFECYCLESTATUS char(150), WORKORDERID char(20), SLOPE double, MATERIAL char(150), SOURCE char(150), OPERATIONALAREA char(150), DIAMETER char(150), MXASSETNUM char(20), MRC char(8), WRNTY_START date, WRNTY_END date, EDIT_DATE date, EDIT_BY char(100), DIAMETERINT double, mxsiteid char(8), SHAPE.STLength() double
    -> ChangeDetector_4 [input 2]
ChangeDetector_4
    BLANK_AND_MISSING_DIFFER = No
    MATCH = NONE
    MATCHATTRS = MXASSETNUM
    MATCH_ALL = No
    LENIENT_MATCH = no
    ADDED -> AttributeCreator_3
AttributeCreator_3
    ATTR_LIST = mxcreationstate,1
    -> MAXIMOGIS.WATER_GRAVITY_MAIN (writer GEODATABASE_SDE_2)
MAXIMOGIS.WATER_GRAVITY_MAIN (writer GEODATABASE_SDE_2)
    attributes: geodb_oid integer, OBJECTID integer, FACILITYID char(20), INSTALLDATE date, LIFECYCLESTATUS char(150), WORKORDERID char(20), SLOPE double, MATERIAL char(150), SOURCE char(150), OPERATIONALAREA char(150), DIAMETER char(150), MRC char(8), WRNTY_START date, WRNTY_END date, EDIT_DATE date, EDIT_BY char(100), DIAMETERINT double, MXSITEID char(8), MXASSETNUM char(20), MXCREATIONSTATE smallint, ROWSTAMP integer, MXASSETUID integer, SHAPE_STLength__ double
MAXIMOGIS.WATER_HYDRANT (reader GEODATABASE_SDE_1)
    attributes: geodb_oid integer, OBJECTID integer, FACILITYID char(20), INSTALLDATE date, LIFECYCLESTATUS char(150), WORKORDERID char(20), ELEVATION double, SOURCE char(150), OLDWATERDEPARTMENT integer, OPERATIONALAREA char(150), LOCATIONDESCRIPTION char(50), MAINDIAMETER char(150), MRC char(8), AGENCY char(150), EDIT_DATE date, EDIT_BY char(100), MXASSETNUM char(20), MXCREATIONSTATE smallint, MXSITEID char(8), ROWSTAMP integer, hydrant_type char(50)
    -> ChangeDetector_5 [input 1]
MAXIMOGIS.TEMP_HYDRANT (reader GEODATABASE_SDE_1)
    attributes: geodb_oid integer, OBJECTID integer, FACILITYID char(20), INSTALLDATE date, LIFECYCLESTATUS char(150), WORKORDERID char(20), ELEVATION double, SOURCE char(150), OLDWATERDEPARTMENT integer, OPERATIONALAREA char(150), LOCATIONDESCRIPTION char(50), MAINDIAMETER char(150), MXASSETNUM char(20), MRC char(8), AGENCY char(150), EDIT_DATE date, EDIT_BY char(100), mxsiteid char(8), hydrant_type char(50)
    -> ChangeDetector_5 [input 2]
ChangeDetector_5
    BLANK_AND_MISSING_DIFFER = No
    MATCH = NONE
    MATCHATTRS = MXASSETNUM
    MATCH_ALL = No
    LENIENT_MATCH = no
    ADDED -> AttributeCreator_4
AttributeCreator_4
    ATTR_LIST = mxcreationstate,1
    -> MAXIMOGIS.WATER_HYDRANT (writer GEODATABASE_SDE_2)
MAXIMOGIS.WATER_HYDRANT (writer GEODATABASE_SDE_2)
    attributes: geodb_oid integer, OBJECTID integer, FACILITYID char(20), INSTALLDATE date, LIFECYCLESTATUS char(150), WORKORDERID char(20), ELEVATION double, SOURCE char(150), OLDWATERDEPARTMENT integer, OPERATIONALAREA char(150), LOCATIONDESCRIPTION char(50), MAINDIAMETER char(150), MRC char(8), AGENCY char(150), EDIT_DATE date, EDIT_BY char(100), MXASSETNUM char(20), MXCREATIONSTATE smallint, MXSITEID char(8), ROWSTAMP integer, hydrant_type char(50)
MAXIMOGIS.WATER_LATERAL_LINE (reader GEODATABASE_SDE_1)
    attributes: geodb_oid integer, OBJECTID integer, FACILITYID char(20), INSTALLDATE date, LIFECYCLESTATUS char(150), SUBTYPE char(150), WORKORDERID char(20), RENEWALDATE date, LOCATIONDESCRIPTION char(50), MATERIAL char(150), DIAMETER char(150), MRC char(8), EDIT_DATE date, EDIT_BY char(100), MXSITEID char(8), MXASSETNUM char(20), MXCREATIONSTATE smallint, ROWSTAMP integer, MXASSETUID integer, SHAPE.STLength() double
    -> ChangeDetector_6 [input 1]
MAXIMOGIS.TEMP_LATERAL_LINE (reader GEODATABASE_SDE_1)
    attributes: geodb_oid integer, OBJECTID integer, FACILITYID char(20), INSTALLDATE date, LIFECYCLESTATUS char(150), SUBTYPE char(150), WORKORDERID char(20), RENEWALDATE date, LOCATIONDESCRIPTION char(50), MATERIAL char(150), DIAMETER char(150), MXASSETNUM char(20), MRC char(8), EDIT_DATE date, EDIT_BY char(100), mxsiteid char(8), SHAPE.STLength() double
    -> ChangeDetector_6 [input 2]
ChangeDetector_6
    BLANK_AND_MISSING_DIFFER = No
    MATCH = NONE
    MATCHATTRS = MXASSETNUM
    MATCH_ALL = No
    LENIENT_MATCH = no
    ADDED -> AttributeCreator_5
AttributeCreator_5
    ATTR_LIST = mxcreationstate,1
    -> MAXIMOGIS.WATER_LATERAL_LINE (writer GEODATABASE_SDE_2)
MAXIMOGIS.WATER_LATERAL_LINE (writer GEODATABASE_SDE_2)
    attributes: geodb_oid integer, OBJECTID integer, FACILITYID char(20), INSTALLDATE date, LIFECYCLESTATUS char(150), SUBTYPE char(150), WORKORDERID char(20), RENEWALDATE date, LOCATIONDESCRIPTION char(50), MATERIAL char(150), DIAMETER char(150), MRC char(8), EDIT_DATE date, EDIT_BY char(100), MXSITEID char(8), MXASSETNUM char(20), MXCREATIONSTATE smallint, ROWSTAMP integer, MXASSETUID integer, SHAPE_STLength__ double
MAXIMOGIS.TEMP_SYSTEM_VALVE (reader GEODATABASE_SDE_1)
    attributes: geodb_oid integer, OBJECTID integer, FACILITYID char(20), INSTALLDATE date, WORKORDERID char(20), ELEVATION double, BYPASSVALVE char(150), DIRECTIONTOCLOSE char(150), CURRENTLYOPEN char(150), MOTORIZED char(150), NORMALLYOPEN char(150), TURNSTOCLOSE smallint, VALVESIZE char(150), LOCATIONDESCRIPTION char(50), OPERATIONALAREA char(150), LIFECYCLESTATUS char(150), SOURCE char(150), OLDWATERDEPARTMENT integer, VALVETYPE char(150), SUBTYPE char(150), MXASSETNUM char(20), MRC char(8), EDIT_DATE date, EDIT_BY char(100), mxsiteid char(8), mxcreationstate smallint, mxassetuid integer
    -> ChangeDetector_7 [input 2]
ChangeDetector_7
    BLANK_AND_MISSING_DIFFER = No
    MATCH = NONE
    MATCHATTRS = MXASSETNUM
    MATCH_ALL = No
    LENIENT_MATCH = no
    ADDED -> AttributeCreator_6
AttributeCreator_6
    ATTR_LIST = mxcreationstate,1
    -> MAXIMOGIS.WATER_SYSTEM_VALVE (writer GEODATABASE_SDE_2)
MAXIMOGIS.WATER_SYSTEM_VALVE (writer GEODATABASE_SDE_2)
    attributes: geodb_oid integer, OBJECTID integer, FACILITYID char(20), INSTALLDATE date, WORKORDERID char(20), ELEVATION double, BYPASSVALVE char(150), DIRECTIONTOCLOSE char(150), CURRENTLYOPEN char(150), MOTORIZED char(150), NORMALLYOPEN char(150), TURNSTOCLOSE smallint, VALVESIZE char(150), LOCATIONDESCRIPTION char(50), OPERATIONALAREA char(150), LIFECYCLESTATUS char(150), SOURCE char(150), OLDWATERDEPARTMENT integer, VALVETYPE char(150), SUBTYPE char(150), MRC char(8), EDIT_DATE date, EDIT_BY char(100), MXSITEID char(8), MXASSETNUM char(20), MXCREATIONSTATE smallint, ROWSTAMP integer, MXASSETUID integer
MAXIMOGIS.WATER_SAMPLE_SITES (reader GEODATABASE_SDE_1)
    attributes: geodb_oid integer, OBJECTID integer, FIELD1 integer, UNIQUE_CODE char(5), SITE_NAME char(50), ADDRESS char(50), CITY char(25), JANUARY char(10), FEBRUARY char(10), MARCH char(10), APRIL char(10), MAY char(10), JUNE char(10), JULY char(10), AUGUST char(10), SEPTEMBER char(10), OCTOBER char(10), NOVEMBER char(10), DECEMBER char(10), ZONE char(30), MRC char(8), WRNTY_START date, WRNTY_END date, EDIT_DATE date, EDIT_BY char(100), MXSITEID char(8), MXASSETNUM char(20), MXCREATIONSTATE smallint, ROWSTAMP integer, MXASSETUID integer
    -> ChangeDetector_8 [input 1]
MAXIMOGIS.TEMP_SAMPLE_SITES (reader GEODATABASE_SDE_1)
    attributes: geodb_oid integer, OBJECTID integer, FIELD1 integer, UNIQUE_CODE char(5), SITE_NAME char(50), ADDRESS char(50), CITY char(25), JANUARY char(10), FEBRUARY char(10), MARCH char(10), APRIL char(10), MAY char(10), JUNE char(10), JULY char(10), AUGUST char(10), SEPTEMBER char(10), OCTOBER char(10), NOVEMBER char(10), DECEMBER char(10), ZONE char(30), MXASSETNUM char(20), MRC char(8), WRNTY_START date, WRNTY_END date, EDIT_DATE date, EDIT_BY char(100), mxsiteid char(8)
    -> ChangeDetector_8 [input 2]
ChangeDetector_8
    BLANK_AND_MISSING_DIFFER = No
    MATCH = NONE
    MATCHATTRS = MXASSETNUM
    MATCH_ALL = No
    LENIENT_MATCH = no
    ADDED -> AttributeCreator_7
AttributeCreator_7
    ATTR_LIST = mxcreationstate,1
    -> MAXIMOGIS.WATER_SAMPLE_SITES (writer GEODATABASE_SDE_2)
MAXIMOGIS.WATER_SAMPLE_SITES (writer GEODATABASE_SDE_2)
    attributes: geodb_oid integer, OBJECTID integer, FIELD1 integer, UNIQUE_CODE char(5), SITE_NAME char(50), ADDRESS char(50), CITY char(25), JANUARY char(10), FEBRUARY char(10), MARCH char(10), APRIL char(10), MAY char(10), JUNE char(10), JULY char(10), AUGUST char(10), SEPTEMBER char(10), OCTOBER char(10), NOVEMBER char(10), DECEMBER char(10), ZONE char(30), MRC char(8), WRNTY_START date, WRNTY_END date, EDIT_DATE date, EDIT_BY char(100), MXSITEID char(8), MXASSETNUM char(20), MXCREATIONSTATE smallint, ROWSTAMP integer, MXASSETUID integer
MAXIMOGIS.WATER_UNDERGROUND_ENCLOSURE (reader GEODATABASE_SDE_1)
    attributes: geodb_oid integer, OBJECTID integer, FACILITYID char(20), INSTALLDATE date, SUBTYPE char(100), WORKORDERID char(20), ELEVATION double, COVERMATERIAL char(150), COVERTYPE char(20), DEPTH double, INVERTELEVATION double, OPERATIONALAREA char(150), LIFECYCLESTATUS char(150), LOCATIONDESCRIPTION char(75), MRC char(8), EDIT_DATE date, EDIT_BY char(100), MXSITEID char(8), MXASSETNUM char(20), MXCREATIONSTATE smallint, ROWSTAMP integer, MXASSETUID integer, SHAPE.STArea() double, SHAPE.STLength() double
    -> ChangeDetector_9 [input 1]
MAXIMOGIS.TEMP_UNDERGROUND_ENCLOSURE (reader GEODATABASE_SDE_1)
    attributes: geodb_oid integer, OBJECTID integer, FACILITYID char(20), INSTALLDATE date, SUBTYPE char(100), WORKORDERID char(20), ELEVATION double, COVERMATERIAL char(150), COVERTYPE char(20), DEPTH double, INVERTELEVATION double, OPERATIONALAREA char(150), LIFECYCLESTATUS char(150), LOCATIONDESCRIPTION char(75), MXASSETNUM char(20), MRC char(8), EDIT_DATE date, EDIT_BY char(100), mxsiteid char(8), SHAPE.STArea() double, SHAPE.STLength() double
    -> ChangeDetector_9 [input 2]
ChangeDetector_9
    BLANK_AND_MISSING_DIFFER = No
    MATCH = NONE
    MATCHATTRS = MXASSETNUM
    MATCH_ALL = No
    LENIENT_MATCH = no
    ADDED -> AttributeCreator_8
AttributeCreator_8
    ATTR_LIST = mxcreationstate,1
    -> MAXIMOGIS.WATER_UNDERGROUND_ENCLOSURE (writer GEODATABASE_SDE_2)
MAXIMOGIS.WATER_UNDERGROUND_ENCLOSURE (writer GEODATABASE_SDE_2)
    attributes: geodb_oid integer, OBJECTID integer, FACILITYID char(20), INSTALLDATE date, SUBTYPE char(100), WORKORDERID char(20), ELEVATION double, COVERMATERIAL char(150), COVERTYPE char(20), DEPTH double, INVERTELEVATION double, OPERATIONALAREA char(150), LIFECYCLESTATUS char(150), LOCATIONDESCRIPTION char(75), MRC char(8), EDIT_DATE date, EDIT_BY char(100), MXSITEID char(8), MXASSETNUM char(20), MXCREATIONSTATE smallint, ROWSTAMP integer, MXASSETUID integer, SHAPE_STArea__ double, SHAPE_STLength__ double
MAXIMOGIS.WATER_FLUSHING_POINTS (reader GEODATABASE_SDE_1)
    attributes: geodb_oid integer, OBJECTID integer, ADDRESS char(150), SETTING char(150), TYPE char(150), PLANT char(50), LAST_MOD_DATE date, LAST_MOD_BY char(32), MAXIMO_TYPE char(30), MAXIMO_SEQ_NUM integer, ASSET_CODE char(50), MRC char(8), EDIT_DATE date, EDIT_BY char(100), MXASSETNUM char(20), mxsiteid char(8), ROWSTAMP integer, MXASSETUID integer, MXCREATIONSTATE smallint
    -> ChangeDetector_10 [input 1]
MAXIMOGIS.TEMP_WATER_FLUSHING_POINTS (reader GEODATABASE_SDE_1)
    attributes: geodb_oid integer, OBJECTID integer, ADDRESS char(150), SETTING char(150), TYPE char(150), PLANT char(50), LAST_MOD_DATE date, LAST_MOD_BY char(32), MAXIMO_TYPE char(30), MAXIMO_SEQ_NUM integer, ASSET_CODE char(50), MRC char(8), EDIT_DATE date, EDIT_BY char(100), MXASSETNUM char(20), mxsiteid char(8)
    -> ChangeDetector_10 [input 2]
ChangeDetector_10
    BLANK_AND_MISSING_DIFFER = No
    MATCH = NONE
    MATCHATTRS = MXASSETNUM
    MATCH_ALL = No
    LENIENT_MATCH = no
    ADDED -> AttributeCreator_9
AttributeCreator_9
    ATTR_LIST = mxcreationstate,1
    -> MAXIMOGIS.WATER_FLUSHING_POINTS (writer GEODATABASE_SDE_2)
MAXIMOGIS.WATER_FLUSHING_POINTS (writer GEODATABASE_SDE_2)
    attributes: geodb_oid integer, OBJECTID integer, ADDRESS char(150), SETTING char(150), TYPE char(150), PLANT char(50), LAST_MOD_DATE date, LAST_MOD_BY char(32), MAXIMO_TYPE char(30), MAXIMO_SEQ_NUM integer, ASSET_CODE char(50), MRC char(8), EDIT_DATE date, EDIT_BY char(100), MXASSETNUM char(20), mxsiteid char(8), ROWSTAMP integer, MXASSETUID integer, MXCREATIONSTATE smallint
MAXIMOGIS.WATER_BC_ADDRESS (reader GEODATABASE_SDE_1)
    attributes: geodb_oid integer, OBJECTID integer, X double, Y double, ADDRESS char(40), NUMBER integer, APT char(4), PREFIX char(2), STREET_NAME char(30), STREET_TYPE char(4), POSTDIRECTION char(2), CIVICADDRESS_ID double, LOCATION_TYPE integer, CHANGE_DATE date, CITY char(4), ZIPCODE integer, MRC char(8), PINNUM char(15), TRUCKDAY char(10), MXADDRESSCODE char(20), MXSITEID char(8), MXCREATIONSTATE smallint, ROWSTAMP integer, test char(50)
    -> ChangeDetector [input 1]
MAXIMOGIS.TEMP_BC_ADDRESS (reader GEODATABASE_SDE_1)
    attributes: geodb_oid integer, OBJECTID integer, X double, Y double, ADDRESS char(40), NUMBER integer, APT char(4), PREFIX char(2), STREET_NAME char(30), STREET_TYPE char(4), POSTDIRECTION char(2), CIVICADDRESS_ID double, LOCATION_TYPE integer, CHANGE_DATE date, CITY char(4), ZIPCODE integer, MXADDRESSCODE char(20), MRC char(8), PINNUM char(15), TRUCKDAY char(10), mxsiteid char(8)
    -> ChangeDetector [input 2]
ChangeDetector
    BLANK_AND_MISSING_DIFFER = No
    MATCH = NONE
    MATCHATTRS = MXADDRESSCODE
    MATCH_ALL = No
    LENIENT_MATCH = no
    ADDED -> AttributeCreator
AttributeCreator
    ATTR_LIST = mxsiteid,COAWTR,mxcreationstate,1,test,fromfmeadd
    -> MAXIMOGIS.WATER_BC_ADDRESS (writer GEODATABASE_SDE_2)
MAXIMOGIS.WATER_BC_ADDRESS (writer GEODATABASE_SDE_2)
    attributes: geodb_oid integer, OBJECTID integer, X double, Y double, ADDRESS char(40), NUMBER integer, APT char(4), PREFIX char(2), STREET_NAME char(30), STREET_TYPE char(4), POSTDIRECTION char(2), CIVICADDRESS_ID double, LOCATION_TYPE integer, CHANGE_DATE date, CITY char(4), ZIPCODE integer, MRC char(8), PINNUM char(15), TRUCKDAY char(10), MXADDRESSCODE char(20), MXSITEID char(8), MXCREATIONSTATE smallint, ROWSTAMP integer, test char(50)
