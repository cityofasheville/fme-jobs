FME workspace UPDATE_BC_Data_to_maxmio_prod.fmw

Parameters:
- DestDataset_GEODATABASE_SDE = maximosde   # Destination ESRI Geodatabase (ArcSDE) Dataset
- SourceDataset_GEODATABASE_SDE = maximosde   # Source ESRI Geodatabase (ArcSDE) Dataset
- GEODATABASE_SDE_IN_PASSWORD_GEODATABASE_SDE =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   # Password
- GEODATABASE_SDE_OUT_PASSWORD_GEODATABASE_SDE =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   # Password

Readers:
- GEODATABASE_SDE_1: GEODATABASE_SDE from $(SourceDataset_GEODATABASE_SDE)

Writers:
- GEODATABASE_SDE_2: GEODATABASE_SDE to $(DestDataset_GEODATABASE_SDE)

MAXIMOGIS.TEMP_BC_ADDRESS (reader GEODATABASE_SDE_1)
    attributes: geodb_oid integer, OBJECTID integer, X double, Y double, ADDRESS char(40), NUMBER integer, APT char(4), PREFIX char(2), STREET_NAME char(30), STREET_TYPE char(4), POSTDIRECTION char(2), CIVICADDRESS_ID double, LOCATION_TYPE integer, CHANGE_DATE date, CITY char(4), ZIPCODE integer, MXADDRESSCODE char(20), MRC char(8), PINNUM char(15), TRUCKDAY char(10), mxsiteid char(8)
    -> MAXIMOGIS.WATER_BC_ADDRESS (writer GEODATABASE_SDE_2)
MAXIMOGIS.WATER_BC_ADDRESS (writer GEODATABASE_SDE_2)
    attributes: geodb_oid integer, OBJECTID integer, X double, Y double, ADDRESS char(40), NUMBER integer, APT char(4), PREFIX char(2), STREET_NAME char(30), STREET_TYPE char(4), POSTDIRECTION char(2), CIVICADDRESS_ID double, LOCATION_TYPE integer, CHANGE_DATE date, CITY char(4), ZIPCODE integer, MRC char(8), PINNUM char(15), TRUCKDAY char(10), MXADDRESSCODE char(20), MXSITEID char(8), MXCREATIONSTATE smallint, ROWSTAMP integer, test char(50)
MAXIMOGIS.TEMP_BC_STREET (reader GEODATABASE_SDE_1)
    attributes: geodb_oid integer, OBJECTID integer, CENTERLINE_ID double, ROAD_CLASS integer, STREET_PREFIX char(2), STREET_NAME char(30), STREET_TYPE char(4), STREET_POSTDIRECTION char(2), STREET_DUPE char(1), FULL_STREET_NAME char(32), SPEED_LIMIT integer, LANE_COUNT integer, LEFT_FROM_ADDRESS integer, LEFT_TO_ADDRESS integer, RIGHT_FROM_ADDRESS integer, RIGHT_TO_ADDRESS integer, USER_ID char(8), CREATE_DATE date, CHANGE_DATE date, LESN smallint, RESN smallint, LZIP integer, RZIP integer, LCOMMCODE char(4), RCOMMCODE char(4), ROUTE_ID char(20), MXASSETNUM char(20), MRC char(8), MIN_RANGE integer, MAX_RANGE integer,
      mxsiteid char(8), SHAPE.STLength() double
    -> MAXIMOGIS.WATER_BC_STREET (writer GEODATABASE_SDE_2)
MAXIMOGIS.WATER_BC_STREET (writer GEODATABASE_SDE_2)
    attributes: geodb_oid integer, OBJECTID integer, CENTERLINE_ID double, ROAD_CLASS integer, STREET_PREFIX char(2), STREET_NAME char(30), STREET_TYPE char(4), STREET_POSTDIRECTION char(2), STREET_DUPE char(1), FULL_STREET_NAME char(32), SPEED_LIMIT integer, LANE_COUNT integer, LEFT_FROM_ADDRESS integer, LEFT_TO_ADDRESS integer, RIGHT_FROM_ADDRESS integer, RIGHT_TO_ADDRESS integer, USER_ID char(8), CREATE_DATE date, CHANGE_DATE date, LESN smallint, RESN smallint, LZIP integer, RZIP integer, LCOMMCODE char(4), RCOMMCODE char(4), ROUTE_ID char(20), MXASSETNUM char(20), MRC char(8), MIN_RANGE integer, MAX_RANGE integer,
      mxsiteid char(8), SHAPE_STLength__ double
